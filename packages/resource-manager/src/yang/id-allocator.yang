module id-allocator {

  namespace "http://tail-f.com/pkg/id-allocator";
  prefix idalloc;

  import tailf-common {
    prefix tailf;
  }

  import resource-allocator {
    prefix ralloc;
  }

  include id-allocator-alarms {
    revision-date "2017-02-09";
  }

  organization "Tail-f Systems";
  description
    "This module contains a description of an id allocator for defining pools
     of id:s. This can for instance be used when allocating VLAN ids.
     This module contains configuration schema of the id allocator. For the
     operational schema, please see the id-allocator-oper module.";

  revision 2017-08-14 {
    description
      "2.2
      Enhancements:
       Removed 'disable', add 'enable' for alarms.
       This means that if you want alarms you need to enable this explicitly
       now.
      ";
  }

  revision 2017-02-09 {
    description
      "2.1
      Enhancements:
       Added support for alarms
      ";
  }

  revision 2015-12-28 {
     description "2nd revision. Added support for allocation methods.";
  }

  revision 2015-10-20 {
     description "Initial revision.";
  }

  grouping range-grouping {
    leaf start {
      type uint32;
      mandatory true;
    }
    leaf end {
      type uint32;
      mandatory true;
      must ". >= ../start" {
        error-message "range end must be greater or equal to range start";
        tailf:dependency "../start";
      }
    }
  }

  // This is the interface
  augment "/ralloc:resource-pools" {
    list id-pool {
      key "name";
      container range {
        description "The range the resource-pool should contain";
        uses range-grouping;
      }
      list exclude {
        key "start end";
        leaf stop-allocation {
          type boolean;
          default "false";
        }
        uses range-grouping;
        tailf:cli-suppress-mode;
      }
      uses ralloc:resource-pool-grouping {
        augment "allocation/response/response-choice/ok" {
          leaf id {
            type uint32;
          }
        }
      }
      container alarms {
        leaf enabled {
          type empty;
          description "Set this leaf to enable alarms";
        }
        leaf low-threshold-alarm {
          type uint8 {
            range "0 .. 100";
          }
          default 10;
          description "Change the value for when the low threshold alarm is
                       raised. The value describes the percentage IDs left in
                       the pool. The default is to raise the alarm when there
                       are ten (10) percent IDs left in the pool.";
                       
        }
      }
      description "The state of the id-pool.";
      tailf:info "Id pool";
    }
  }

  //augmenting the request/responses form resource-manager
  augment "/ralloc:resource-pools/id-pool/allocation/request" {
    leaf sync {
      type boolean;
      default "false";
      description "Synchronize allocation with all other allocation
                   with same allocation id in other pools";
      tailf:info "Synchronize allocation id with other pools";
    }
    leaf id {
      type uint32;
      description "The specific id to sync with";
      tailf:info "Request a specific id";
    }
    container method {
      choice method {
        default firstfree;
        case firstfree {
          leaf firstfree {
            type empty;
            description "The default method to allocating a new id
                          is using the first free method. Using this
                          allocation method might mean that an id is reused
                          quickly which might not be what one wants nor is
                          supported in lower layers.";
            tailf:info "Default method used to request a new id.";
          }
        }
        case roundrobin {
          leaf roundrobin {
            type empty;
            description "Pick the next available id using a round
                           robin approach. Earlier used id:s will not be
                           reused until the range is exhausted and allocation
                           restarts from the start of the range again.
                           
                         Note that sync will override round robin.";
            tailf:info "Round robin method used to request a new id.";
          }
        }
      }
    }
  }
}
