module ipaddress-allocator {

  namespace "http://tail-f.com/pkg/ipaddress-allocator";

  prefix ipalloc;

  import tailf-common {
    prefix tailf;
  }

  import ietf-inet-types {
    prefix inet;
  }

  import resource-allocator {
    prefix ralloc;
  }

  include ipaddress-allocator-alarms {
    revision-date "2017-02-09";
  }

  organization "Tail-f Systems";
  description
    "This module contains a description of an IP address allocator for defining
     pools of IPs and allocating addresses from these.
     This module contains configuration schema of the id allocator. For the
     operational schema, please see the id-allocator-oper module.";

  revision 2018-02-27 {
    description
      "Introduce the 'invert' field in the request container that enables
       one to allocate the same size network regardless of the network
       type (IPv4/IPv6) in a pool by using the inverted cidr.";
  }

  revision 2017-08-14 {
    description
      "2.2
      Enhancements:
       Removed 'disable', add 'enable' for alarms.
       This means that if you want alarms you need to enable this explicitly
       now.
      ";
  }

  revision 2017-02-09 {
    description
      "1.2
      Enhancements:
       Added support for alarms
      ";
  }

  revision 2016-01-29 {
    description
      "1.1
      Enhancements:
       Added support for defining pools using IP address ranges.
      ";
  }

  revision 2015-10-20 {
    description "Initial revision.";
  }

  // This is the interface
  augment "/ralloc:resource-pools" {
    list ip-address-pool {
      tailf:info "IP Address pools";
      key name;

      uses ralloc:resource-pool-grouping {
        augment "allocation/request" {
          leaf subnet-size {
            tailf:info "Size of the subnet to be allocated.";
            type uint8 {
              range "1..128";
            }
            mandatory true;
          }

          leaf invert-subnet-size {
            description
              "By default subnet-size is considered equal to the cidr, but by
               setting this leaf the subnet-size will be the \"inverted\" cidr.
               I.e: If one sets subnet-size to 8 with this leaf unset 2^24
               addresses will be allocated for a IPv4 pool and in a IPv6 pool
               2^120 addresses will be allocated. By setting this leaf only
               2^8 addresses will be allocated in either a  IPv4 or a IPv6
               pool.";
            type empty;
          }
        }
        augment "allocation/response/response-choice/ok" {
          leaf subnet {
            type inet:ip-prefix;
          }
          leaf from {
            type inet:ip-prefix;
          }
        }
      }

      leaf auto-redeploy {
        tailf:info "Automatically re-deploy services when an IP address is "
          +"re-allocated";
        type boolean;
        default "true";
      }

      list subnet {
        key "address cidrmask";
        tailf:cli-suppress-mode;
        description
          "List of subnets belonging to this pool. Subnets may not overlap.";

        must "(contains(address, '.') and cidrmask <= 32) or
              (contains(address, ':') and cidrmask <= 128)" {
          error-message "cidrmask is too long";
        }

        tailf:validate ipa_validate {
          tailf:dependency ".";
        }

        leaf address {
          type inet:ip-address;
        }

        leaf cidrmask {
          type uint8 {
            range "1..128";
          }
        }
      }

      list exclude {
        key "address cidrmask";
        tailf:cli-suppress-mode;
        description "List of subnets to exclude from this pool. May only "
          +"contains elements that are subsets of elements in the list of "
          +"subnets.";

        must "(contains(address, '.') and cidrmask <= 32) or
              (contains(address, ':') and cidrmask <= 128)" {
          error-message "cidrmask is too long";
        }

        tailf:validate ipa_validate {
          tailf:dependency ".";
        }

        leaf address {
          type inet:ip-address;
        }

        leaf cidrmask {
          type uint8 {
            range "1..128";
          }
        }
      }

      list range {
        key "from to";
        tailf:cli-suppress-mode;
        description
          "List of IP ranges belonging to this pool, inclusive. If your "
          +"pool of IP addresses does not conform to a convenient set of "
          +"subnets it may be easier to describe it as a range. "
          +"Note that the exclude list does not apply to ranges, but of "
          +"course a range may not overlap a subnet entry.";

        tailf:validate ipa_validate {
          tailf:dependency ".";
        }

        leaf from {
          type inet:ip-address-no-zone;
        }

        leaf to {
          type inet:ip-address-no-zone;
        }

        must "(contains(from, '.') and contains(to, '.')) or
              (contains(from, ':') and contains(to, ':'))" {
          error-message
            "IP addresses defining a range must agree on IP version.";
        }
      }
      container alarms {
        leaf enabled {
          type empty;
          description "Set this leaf to enable alarms";
        }

        leaf low-threshold-alarm {
          type uint8 {
            range "0 .. 100";
          }
          default 10;
          description  "Change the value for when the low threshold alarm is
                       raised. The value describes the percentage IPs left in
                       the pool. The default is to raise the alarm when there
                       are ten (10) percent IPs left in the pool.";
        }
      }
    }
  }
}
