module ip-loop-service {

  namespace "dummy-ip-http://example.com/loop-service";
  prefix ip-vl;

  import tailf-common {
    prefix tailf;
  }

  import tailf-ncs {
    prefix ncs;
  }

  import resource-allocator {
    prefix ralloc;
  }

  import ipaddress-allocator {
    prefix ipalloc;
  }

  description
    "This service creates a loop iface/unit on all routers
     in our network. ";

  revision 2013-01-08 {
    description
      "Initial revision.";
  }

  augment /ncs:services {

    list ip-loop {

      key name;
      leaf name {
        tailf:info "Unique service id";
        tailf:cli-allow-range;
        type string;
      }

      uses ncs:service-data;
      ncs:servicepoint ip-loopspnt;

      leaf device {
        tailf:info "Device to enable the loopback interface on";
        type leafref {
          path "/ncs:devices/ncs:device/ncs:name";
        }
        mandatory true;
      }

      leaf pool {
        type leafref {
          path "/ralloc:resource-pools/ipalloc:ip-address-pool/ipalloc:name";
        }
        mandatory true;
      }

      leaf unit {
        tailf:info "Loopback interface number.";
        type string {
          pattern "([0-9\\.])+";
          tailf:info "<0-2147483647>;;Loopback interface number";
        }
        mandatory true;
      }
      leaf description {
        type string;
        mandatory true;
      }
    }

    list ip-loop-python {

      key name;
      leaf name {
        tailf:info "Unique service id";
        tailf:cli-allow-range;
        type string;
      }

      uses ncs:service-data;
      ncs:servicepoint ip-loopspnt-python;

      leaf pool {
        type leafref {
          path "/ralloc:resource-pools/ipalloc:ip-address-pool/ipalloc:name";
        }
        mandatory true;
      }

      leaf cidr-length {
        type uint8 {
          range "1..32";
        }
        mandatory true;
      }
    }
  }
}
