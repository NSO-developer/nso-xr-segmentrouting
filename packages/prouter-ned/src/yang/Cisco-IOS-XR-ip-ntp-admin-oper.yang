module Cisco-IOS-XR-ip-ntp-admin-oper {

  /*** NAMESPACE / PREFIX DEFINITION ***/

  namespace "http://cisco.com/ns"+
    "/yang/Cisco-IOS-XR-ip-ntp-admin-oper";


  prefix "ip-ntp-admin-oper";

  /*** LINKAGE (IMPORTS / INCLUDES) ***/

  include Cisco-IOS-XR-ip-ntp-admin-oper-sub1 {
    revision-date 2017-09-07;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-ntp package
     admin-plane operational data.

     This module contains definitions
     for the following management objects:
       ntp: NTP admin operational data

     Copyright (c) 2013-2018 by Cisco Systems, Inc.
     All rights reserved.";

  revision "2017-09-07" {
    description
      "Fixed type translation error.";
  }

  revision "2015-11-09" {
    description
      "IOS XR 6.0 revision.";
  }


  container ntp {
    config false;
    description "NTP admin operational data";

    container racks {
      description "Rack-specific NTP operational data";

      list rack {
        key "number";
        description "NTP operational data for a particular rack";

        container slots {
          description "Node-specific NTP operational data";

          list slot {
            key "number";
            description
              "NTP operational data for a particular slot";

            container instances {
              description "Instance-specific NTP operational data";

              list instance {
                key "number";
                description
                  "NTP operational data for a particular
                  instance";

                container status {
                  description "Status of NTP peer(s)";
                  uses NTP-EDM-STATUS-RESULT;
                }

                container associations {
                  description "NTP Associations information";
                  uses NTP-EDM-ASSOC-SUMMARY-RESULT;
                }

                container associations-detail {
                  description "NTP Associations Detail information";
                  uses NTP-EDM-ASSOC-DETAIL-RESULT;
                }
                leaf number {
                  type uint32;
                  description "The instance number";
                }
              }
            }
            leaf number {
              type uint32;
              description "The slot number";
            }
          }
        }
        leaf number {
          type uint32;
          description "The rack number";
        }
      }
    }
  }
}
