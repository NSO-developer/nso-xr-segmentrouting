module Cisco-IOS-XR-mpls-oam-oper {

  /*** NAMESPACE / PREFIX DEFINITION ***/

  namespace "http://cisco.com/ns/yang/Cisco-IOS-XR-mpls-oam-oper";


  prefix "mpls-oam-oper";

  /*** LINKAGE (IMPORTS / INCLUDES) ***/

  import Cisco-IOS-XR-types { prefix "xr"; }

  include Cisco-IOS-XR-mpls-oam-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR mpls-oam package operational data.

     This module contains definitions
     for the following management objects:
       mpls-oam: MPLS OAM operational data

     Copyright (c) 2013-2018 by Cisco Systems, Inc.
     All rights reserved.";

  revision "2015-11-09" {
    description
      "IOS XR 6.0 revision.";
  }


  container mpls-oam {
    config false;
    description "MPLS OAM operational data";

    container interface {
      description "MPLS OAM interface operational data";

      container briefs {
        description "MPLS OAM interface detail data";

        list brief {
          key "interface-name";
          description "MPLS OAM interface operational data";
          leaf interface-name {
            type xr:Interface-name;
            description "Interface name";
          }
          uses LSPV-INTERFACE-INFO-BRIEF;
        }
      }

      container details {
        description "MPLS OAM interface detail data";

        list detail {
          key "interface-name";
          description "MPLS OAM interface operational data";
          leaf interface-name {
            type xr:Interface-name;
            description "Interface name";
          }
          uses LSPV-INTERFACE-INFO;
        }
      }
    }

    container packet {
      description "LSPV packet counters operational data";
      uses LSPV-PACKET-STATISTICS;
    }

    container global {
      description "LSPV global counters operational data";
      uses LSPV-GLOBAL-TYPE;
    }
  }
}
