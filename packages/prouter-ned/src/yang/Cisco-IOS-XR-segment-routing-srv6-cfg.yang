module Cisco-IOS-XR-segment-routing-srv6-cfg {

  /*** NAMESPACE / PREFIX DEFINITION ***/

  namespace "http://cisco.com/ns/yang"+
    "/Cisco-IOS-XR-segment-routing-srv6-cfg";


  prefix "segment-routing-srv6-cfg";

  /*** LINKAGE (IMPORTS / INCLUDES) ***/

  import ietf-inet-types { prefix "inet"; }

  import Cisco-IOS-XR-types { prefix "xr"; }

  import Cisco-IOS-XR-segment-routing-srv6-datatypes {
    prefix "dt1";
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR segment-routing-srv6 package configuration.

     This module contains definitions
     for the following management objects:
       srv6: Segment Routing with IPv6 dataplane

     Copyright (c) 2013-2018 by Cisco Systems, Inc.
     All rights reserved.";

  revision "2015-11-09" {
    description
      "IOS XR 6.0 revision.";
  }


  container srv6 {
    description "Segment Routing with IPv6 dataplane";

    container locators {
      description "Configure SRv6 locators";

      list locator {
        key "name";
        description "Configure a SRv6 locator";

        container prefix {
          presence "Indicates a prefix node is configured.";
          description "Specify locator prefix value";
          leaf prefix {
            type inet:ip-address-no-zone;
            mandatory true;
            description "IPv6 Prefix";
          }
          leaf prefix-length {
            type dt1:Srv6-locator-len;
            mandatory true;
            description "Prefix length";
          }
        }
        leaf locator-enable {
          type empty;
          description "Enable a SRv6 locator";
        }
        leaf name {
          type dt1:Srv6-locator-name;
          description "Locator name";
        }
      }
    }

    container logging {
      description "Enable logging";
      leaf locator-status {
        type empty;
        description "Enable logging for locator status changes";
      }
    }

    container encapsulation {
      presence "Indicates a encapsulation node is configured.";
      description "Configure encapsulation related parameters";
      leaf source-address {
        type inet:ip-address-no-zone;
        mandatory true;
        description "Configure a source address (for T.Encap)";
      }
    }
    leaf enable {
      type empty;
      description "Enable SRv6";
    }
  }
}
