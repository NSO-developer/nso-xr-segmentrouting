module Cisco-IOS-XR-snmp-ifmib-cfg {

  /*** NAMESPACE / PREFIX DEFINITION ***/

  namespace "http://cisco.com/ns/yang/Cisco-IOS-XR-snmp-ifmib-cfg";


  prefix "snmp-ifmib-cfg";

  /*** LINKAGE (IMPORTS / INCLUDES) ***/

  import Cisco-IOS-XR-types { prefix "xr"; }

  import Cisco-IOS-XR-snmp-agent-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR snmp-ifmib package configuration.

     This YANG module augments the
       Cisco-IOS-XR-snmp-agent-cfg,
     module with configuration data.

     Copyright (c) 2013-2018 by Cisco Systems, Inc.
     All rights reserved.";

  revision "2017-05-01" {
    description
      "Fixing backward compatibility error in module.";
  }

  revision "2015-05-14" {
    description
      "IOS XR 5.3.2 revision.";
  }

  revision "2015-01-07" {
    description
      "IOS XR 5.3.1 revision.";
  }


  augment "/a1:mib" {

    container interface-mib {
      description "Interface MIB configuration";

      container interfaces {
        description
          "Enter the SNMP interface configuration commands";

        list interface {
          key "interface-name";
          description "Interface to configure";
          leaf link-up-down {
            type boolean;
            description "Enable or disable LinkUpDown notification";
          }
          leaf index-persistence {
            type boolean;
            description "Enable or disable index persistence";
          }
          leaf interface-name {
            type xr:Interface-name;
            description "The name of the interface";
          }
        }
      }

      container notification {
        description "MIB notification configuration";
        leaf link-ietf {
          type empty;
          description
            "Set the varbind of linkupdown trap to the RFC
            specified varbinds (default cisco)";
        }
      }

      container subsets {
        description "Add configuration for an interface subset";

        list subset {
          key "subset-id";
          description
            "Subset priorityID to group ifNames based on
            Regular Expression";

          container link-up-down {
            description "SNMP linkUp and linkDown notifications";
            leaf enable {
              type boolean;
              description
                "Enable or disable linkupdown notification";
            }
            leaf regular-expression {
              type string;
              description "Regular expression to match ifName";
            }
          }
          leaf subset-id {
            type uint32 {
              range "1..255";
            }
            description "The interface subset PriorityID";
          }
        }
      }
      leaf internal-cache {
        type uint32 {
          range "0..60";
        }
        default "15";
        description "Get cached interface statistics";
      }
      leaf interface-alias-long {
        type empty;
        description
          "Enable support for ifAlias values longer than
          64 characters";
      }
      leaf ip-subscriber {
        type empty;
        description "Enable IP subscriber interfaces in IFMIB";
      }
      leaf interface-index-persistence {
        type empty;
        description "Enable ifindex persistence";
      }
      leaf statistics-cache {
        type empty;
        description "Enable cached interface statistics";
      }
    }
    description
      "This augment extends the configuration data of
      'Cisco-IOS-XR-snmp-agent-cfg'";
  }

  augment "/a1:snmp/a1:notification/a1:snmp" {
    leaf link-down {
      type empty;
      description "Enable link down notification";
    }
    description
      "This augment extends the configuration data of
      'Cisco-IOS-XR-snmp-agent-cfg'";
  }

  augment "/a1:snmp/a1:notification/a1:snmp" {
    leaf link-up {
      type empty;
      description "Enable link up notification";
    }
    description
      "This augment extends the configuration data of
      'Cisco-IOS-XR-snmp-agent-cfg'";
  }
}
