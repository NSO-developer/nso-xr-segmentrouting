module Cisco-IOS-XR-man-xml-ttyagent-cfg {

  /*** NAMESPACE / PREFIX DEFINITION ***/

  namespace "http://cisco.com/ns/yang"+
    "/Cisco-IOS-XR-man-xml-ttyagent-cfg";


  prefix "man-xml-ttyagent-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR man-xml-ttyagent package configuration.

     This module contains definitions
     for the following management objects:
       xr-xml: XML
       netconf: netconf

     Copyright (c) 2013-2018 by Cisco Systems, Inc.
     All rights reserved.";

  revision "2017-05-01" {
    description
      "Fixing backward compatibility error in module.";
  }

  revision "2015-07-30" {
    description
      "Descriptions updated.";
  }

  revision "2015-01-07" {
    description
      "IOS XR 5.3.1 revision.";
  }


  grouping SESSION {
    description "Common node of default, ssl, tty";

    container session {
      description "Session attributes";
      leaf timeout {
        type uint32 {
          range "1..1440";
        }
        units "minute";
        description "Timeout in minutes";
      }
    }
  }

  grouping VRF-TABLE {
    description "Common node of default, ssl";

    container vrfs {
      description "List of VRFs";

      list vrf {
        key "vrf-name";
        description "A specific VRF";
        leaf ipv6-access-list {
          type xr:Cisco-ios-xr-string {
            length "1..32";
          }
          description "IPv6 Transport Access list for VRF";
        }
        leaf ipv4-access-list {
          type xr:Cisco-ios-xr-string {
            length "1..32";
          }
          description "IPv4 Transport Access list for VRF";
        }
        leaf access-list {
          type xr:Cisco-ios-xr-string {
            length "1..32";
          }
          description "Access list for XML agent";
        }
        leaf shutdown {
          type empty;
          description
            "Shutdown default VRF. This is applicable only
            for VRF default.";
        }
        leaf vrf-name {
          type xr:Cisco-ios-xr-string {
            length "1..32";
          }
          description "VRF name";
        }
      }
    }
  }

  grouping ITERATION-SIZE {
    description "Common node of default, ssl, tty";
    leaf iteration-size {
      type uint32 {
        range "0..100000";
      }
      units "kilobyte";
      default "48";
      description
        "Iterator size, in KBytes, of the XML response.
        Specify 0 to turn off the XML response iterator.";
    }
  }

  grouping STREAMING-SIZE {
    description "Common node of default, ssl, tty";
    leaf streaming-size {
      type uint32 {
        range "1..100000";
      }
      units "kilobyte";
      description "Streaming size, in KBytes, of the XML response.";
    }
  }

  grouping THROTTLE {
    description "Common node of default, ssl, tty";

    container throttle {
      description "XML agent throttling";
      leaf process-rate {
        type uint32 {
          range "1000..30000";
        }
        description "Process rate in number of XML tags per second";
      }
      leaf memory {
        type uint32 {
          range "100..1024";
        }
        units "megabyte";
        default "300";
        description "Size of memory usage, in MBytes, per session.";
      }
    }
  }

  grouping ENABLE {
    description "Common node of default, ssl, tty";
    leaf enable {
      type empty;
      description "Enable specified XML agent";
    }
  }

  container xr-xml {
    description "XML";

    container agent {
      description "XML agent";

      container default {
        description "XML default dedicated agent";
        leaf ipv6-enable {
          type boolean;
          description "IPv6 Transport State";
        }
        leaf ipv4-disable {
          type boolean;
          description "TRUE to disable IPV4";
        }
        uses SESSION;
        uses ITERATION-SIZE;
        uses THROTTLE;
        uses ENABLE;
        uses STREAMING-SIZE;
        uses VRF-TABLE;
      }

      container tty {
        description "XML TTY agent";
        uses SESSION;
        uses ITERATION-SIZE;
        uses THROTTLE;
        uses ENABLE;
        uses STREAMING-SIZE;
      }

      container ssl {
        description "XML SSL agent";
        uses SESSION;
        uses ITERATION-SIZE;
        uses THROTTLE;
        uses ENABLE;
        uses STREAMING-SIZE;
        uses VRF-TABLE;
      }
    }
  }

  container netconf {
    description "netconf";

    container agent {
      description "XML agent";

      container tty {
        description "NETCONF agent over TTY";

        container throttle {
          description "NETCONF agent throttling";
          leaf memory {
            type uint32 {
              range "100..1024";
            }
            units "megabyte";
            default "300";
            description
              "Size of memory usage, in MBytes, per session.";
          }
          leaf offload-memory {
            type uint32 {
              range "0..12000";
            }
            units "megabyte";
            default "0";
            description
              "Size of memory usage, in MBytes, per session.";
          }
          leaf process-rate {
            type uint32 {
              range "1000..30000";
            }
            description
              "Process rate in number of XML tags per second";
          }
        }

        container session {
          description "Session attributes";
          leaf timeout {
            type uint32 {
              range "1..1440";
            }
            units "minute";
            description "Timeout in minutes";
          }
        }
        leaf enable {
          type empty;
          description "Enable specified NETCONF agent";
        }
      }
    }
  }
}
