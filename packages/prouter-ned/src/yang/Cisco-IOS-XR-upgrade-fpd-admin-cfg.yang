module Cisco-IOS-XR-upgrade-fpd-admin-cfg {

  /*** NAMESPACE / PREFIX DEFINITION ***/

  namespace "http://cisco.com/ns/yang"+
    "/Cisco-IOS-XR-upgrade-fpd-admin-cfg";


  prefix "upgrade-fpd-admin-cfg";

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR upgrade-fpd package admin-plane configuration.

     This module contains definitions
     for the following management objects:
       fpd: Configuration for fpd auto-upgrade

     Copyright (c) 2013-2018 by Cisco Systems, Inc.
     All rights reserved.";

  revision "2015-11-09" {
    description
      "IOS XR 6.0 revision.";
  }


  container fpd {
    description "Configuration for fpd auto-upgrade";
    leaf auto-upgrade {
      type boolean;
      description "Variable for fpd auto-upgrade enable/disable";
    }
    leaf auto-reload {
      type boolean;
      description "Variable for fpd auto-reload enable/disable";
    }
  }
}
