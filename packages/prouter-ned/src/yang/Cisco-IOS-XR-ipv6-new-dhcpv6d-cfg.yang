module Cisco-IOS-XR-ipv6-new-dhcpv6d-cfg {

  /*** NAMESPACE / PREFIX DEFINITION ***/

  namespace "http://cisco.com/ns/yang"+
    "/Cisco-IOS-XR-ipv6-new-dhcpv6d-cfg";


  prefix "ipv6-new-dhcpv6d-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv6-new-dhcpv6d package configuration.

     This module contains definitions
     for the following management objects:
       dhcpv6: None

     Copyright (c) 2013-2018 by Cisco Systems, Inc.
     All rights reserved.";

  revision "2017-09-12" {
    description
      "Added Remote-id config for relay profile";
  }

  revision "2017-09-07" {
    description
      "Fixed type translation error.";
  }

  revision "2017-05-01" {
    description
      "Fixing backward compatibility error in module.";
  }

  revision "2016-10-10" {
    description
      "Moved augment statement to a separate file";
  }

  revision "2015-11-09" {
    description
      "IOS XR 6.0 revision.";
  }

  typedef Insert {
    type enumeration {
      enum local {
        value 0;
        description
          "Insert locally generated/configured Interface
          ID value";
      }
      enum received {
        value 1;
        description "Insert received Interface ID value";
      }
      enum pppoe {
        value 2;
        description "Insert received Interface ID value from SADB";
      }
      enum received-nodefault {
        value 3;
        description "No default Interface ID";
      }
    }
    description "Insert";
  }
  typedef Subscriber-id {
    type enumeration {
      enum pppoe {
        value 3;
        description "Insert Received Subscriber-ID Value from SADB";
      }
    }
    description "Subscriber id";
  }
  typedef Action {
    type enumeration {
      enum allow {
        value 0;
        description "Allow vendor specific DHCP Solicit";
      }
      enum drop {
        value 1;
        description "Drop vendor specific DHCP Solicit";
      }
    }
    description "Action";
  }
  typedef Link-layer-addr {
    type enumeration {
      enum set {
        value 4;
        description "Insert Received LinkLayerAddr Value from SADB";
      }
    }
    description "Link layer addr";
  }

  grouping PROFILE {
    description "Common node of mode-class, default";

    list profile {
      key "profile-name";
      description "Enter proxy or server profile";
      leaf server-mode {
        type empty;
        description "Specify mode-class based Server option";
      }
      leaf proxy-mode {
        type empty;
        description "Specify mode-class based Proxy Option";
      }
      leaf profile-name {
        type xr:Cisco-ios-xr-string {
          length "1..64";
        }
        description "Profile name";
      }
    }
  }

  container dhcpv6 {
    presence "Indicates a dhcpv6 node is configured.";
    description "None";

    container database {
      description
        "Enable DHCP binding database storage to file
        system";
      leaf proxy {
        type empty;
        description
          "Enable DHCP proxy binding database storage to
          file system";
      }
      leaf server {
        type empty;
        description
          "Enable DHCP server binding database storage to
          file system";
      }
      leaf relay {
        type empty;
        description
          "Enable DHCP relay binding database storage to
          file system";
      }
      leaf full-write-interval {
        type uint32 {
          range "1..1440";
        }
        default "10";
        description "Full file write interval (default 10 minutes)";
      }
      leaf incremental-write-interval {
        type uint32 {
          range "1..1440";
        }
        default "1";
        description
          "Incremental file write interval (default 1
          minutes)";
      }
    }

    container profiles {
      description "Table of Profile";

      list profile {
        key "profile-name";
        description "None";

        container relay {
          presence "Indicates a relay node is configured.";
          description "None";

          container helper-addresses {
            description "Table of HelperAddress";

            list helper-address {
              key "vrf-name helper-address";
              description "Specify the server helper address";
              leaf vrf-name {
                type xr:Cisco-ios-xr-string {
                  length "1..32";
                }
                description "VRF name";
              }
              leaf helper-address {
                type inet:ipv6-address-no-zone;
                description "Server Global unicast address";
              }
              leaf enable {
                type empty;
                mandatory true;
                description "Enable";
              }
              leaf src-intf-name {
                type xr:Interface-name;
                description
                  "Helper-address Specific Source Interface";
              }
            }
          }

          container option {
            description "Specify relay option configuration";
            leaf remote-id {
              type string {
                length "1..256";
              }
              description "Enter remote-id value";
            }
          }
          leaf src-intf-name {
            type xr:Interface-name;
            description "Relay profile Source Interface Name";
          }
          leaf enable {
            type empty;
            mandatory true;
            description
              "Enable None. Deletion of this object also
              causes deletion of all associated objects
              under Relay.";
          }
          leaf iana-route-add {
            type empty;
            description "Enable route addition for IANA";
          }
          leaf relay-route-add-disable {
            type empty;
            description "RouteDisable";
          }
        }

        container base {
          presence "Indicates a base node is configured.";
          description "None";

          container default {
            description "Default match option";
            uses PROFILE;
          }

          container match {
            description "Enter match option";

            container mode-classes {
              description "Table of ModeClass";

              list mode-class {
                key "class-name";
                description "Specify PPP/IPoE class option";
                leaf class-name {
                  type xr:Cisco-ios-xr-string {
                    length "1..128";
                  }
                  description "Class name";
                }
                uses PROFILE;
              }
            }
          }
          leaf enable {
            type empty;
            mandatory true;
            description
              "Enable None. Deletion of this object also
              causes deletion of all associated objects
              under Base.";
          }
        }

        container proxy {
          presence "Indicates a proxy node is configured.";
          description "None";

          container interfaces {
            description "Table of Interface";

            list interface {
              key "interface-name";
              description "None";
              leaf interface-id {
                type string;
                description "Physical interface ID";
              }
              leaf interface-name {
                type xr:Interface-name;
                description "Interface to configure";
              }
            }
          }

          container relay {
            description "Specify relay configuration";

            container option {
              description "Specify relay option configuration";

              container interface-id {
                description "Interface Id option";
                leaf insert {
                  type Insert;
                  description "Configure InterfaceID insert type";
                }
              }
              leaf subscriber-id {
                type Subscriber-id;
                description "Configure Received SubscriberID";
              }
              leaf link-layer-addr {
                type Link-layer-addr;
                description "Configure Received link-layer-Addr";
              }
              leaf remote-i-dreceived {
                type uint32;
                description "Set remote-id value from SADB";
              }
              leaf remote-id {
                type string {
                  length "1..256";
                }
                description "Enter remote-id value";
              }
            }
          }

          container vrfs {
            description "VRF related configuration";

            list vrf {
              key "vrf-name";
              description "IPv6 DHCP proxy VRF name";

              container helper-addresses {
                description "Table of HelperAddress";

                list helper-address {
                  key "helper-address";
                  description "DHCPv6 Helper Address";
                  leaf out-interface {
                    type xr:Interface-name;
                    description
                      "DHCPv6 HelperAddress Specific Output
                      Interface";
                  }
                  leaf any-out-interface {
                    type empty;
                    description
                      "DHCPv6 HelperAddress Output Interface";
                  }
                  leaf helper-address {
                    type inet:ipv6-address-no-zone;
                    description "DHCPv6 Helper Address";
                  }
                }
              }
              leaf vrf-name {
                type xr:Cisco-ios-xr-string;
                description "VRF name";
              }
            }
          }

          container authentication {
            description "Authentication username format";
            leaf username {
              type empty;
              description "Set username as DUID";
            }
          }

          container classes {
            description "Table of Class";

            list class {
              key "class-name";
              description "None";

              container helper-addresses {
                description "Table of HelperAddress";

                list helper-address {
                  key "vrf-name helper-address";
                  description "Specify the server helper address";
                  leaf vrf-name {
                    type xr:Cisco-ios-xr-string {
                      length "1..32";
                    }
                    description "VRF name";
                  }
                  leaf helper-address {
                    type inet:ipv6-address-no-zone;
                    description "Server address";
                  }
                }
              }
              leaf link-address {
                type inet:ip-address-no-zone;
                description
                  "IPv6 address to be filled in link-address";
              }
              leaf class-name {
                type xr:Cisco-ios-xr-string {
                  length "1..128";
                }
                description "Class name";
              }
            }
          }

          container sessions {
            description "Change sessions configuration";

            container mac {
              description
                "Throttle DHCP sessions based on MAC address";

              container throttle {
                description
                  "Throttle DHCP sessions from any one MAC
                  address";
                leaf limit {
                  type uint32 {
                    range "1..65535";
                  }
                  description
                    "Number of solicits at which to throttle";
                }
                leaf request {
                  type uint32 {
                    range "1..100";
                  }
                  units "second";
                  description "Throttle request period (in secs)";
                }
                leaf block {
                  type uint32 {
                    range "1..100";
                  }
                  units "second";
                  description "Throttle blocking period (in secs)";
                }
              }
            }
          }
          leaf linkaddress-from-ra-enable {
            type empty;
            description
              "Fill linkaddress in Relay fwd msg with Prefix
              from Router Advertisement for PPPoE sessions";
          }
          leaf route-add-disable {
            type empty;
            description "RouteDisable";
          }
          leaf link-address {
            type inet:ip-address-no-zone;
            description "IPv6 address to be filled in link-address";
          }
          leaf src-intf-name {
            type xr:Interface-name;
            description
              "Create or enter proxy profile Source
              Interface Name";
          }
          leaf enable {
            type empty;
            mandatory true;
            description
              "Enable None. Deletion of this object also
              causes deletion of all associated objects
              under Proxy.";
          }
        }

        container server {
          presence "Indicates a server node is configured.";
          description "None";

          container sessions {
            description "Change sessions configuration";

            container mac {
              description
                "Throttle DHCP sessions based on MAC address";

              container throttle {
                description
                  "Throttle DHCP sessions from any one MAC
                  address";
                leaf limit {
                  type uint32 {
                    range "1..65535";
                  }
                  description
                    "Number of solicits at which to throttle";
                }
                leaf request {
                  type uint32 {
                    range "1..100";
                  }
                  units "second";
                  description "Throttle request period (in secs)";
                }
                leaf block {
                  type uint32 {
                    range "1..100";
                  }
                  units "second";
                  description "Throttle blocking period (in secs)";
                }
              }
            }
          }

          container dns-servers {
            description "DNS servers";
            leaf-list dns-server {
              type inet:ip-address-no-zone;
              max-elements "8";
              description "Server's IPv6 address";
            }
          }

          container classes {
            description "Table of Class";

            list class {
              key "class-name";
              description "None";

              container dns-servers {
                description "DNS servers";
                leaf-list dns-server {
                  type inet:ip-address-no-zone;
                  max-elements "8";
                  description "Server's IPv6 address";
                }
              }

              container lease {
                description "lease";
                leaf infinite {
                  type string;
                  description "Set string";
                }
                leaf days {
                  type uint32 {
                    range "0..365";
                  }
                  units "day";
                  description "Days";
                }
                leaf hours {
                  type uint32 {
                    range "0..23";
                  }
                  units "hour";
                  description "Hours";
                }
                leaf minutes {
                  type uint32 {
                    range "0..59";
                  }
                  units "minute";
                  description "Minutes";
                }
              }
              leaf address-pool {
                type string {
                  length "1..64";
                }
                description "Address pool name";
              }
              leaf domain-name {
                type xr:Cisco-ios-xr-string {
                  length "1..64";
                }
                description "Domain name";
              }
              leaf preference {
                type uint32 {
                  range "1..255";
                }
                description "DHCP Server Preference";
              }
              leaf prefix-pool {
                type string {
                  length "1..64";
                }
                description "Prefix pool name";
              }
              leaf class-name {
                type xr:Cisco-ios-xr-string {
                  length "1..128";
                }
                description "class name";
              }
            }
          }

          container lease {
            description "lease";
            leaf days {
              type uint32 {
                range "0..365";
              }
              units "day";
              description "Days";
            }
            leaf hours {
              type uint32 {
                range "0..23";
              }
              units "hour";
              description "Hours";
            }
            leaf minutes {
              type uint32 {
                range "0..59";
              }
              units "minute";
              description "Minutes";
            }
            leaf infinite {
              type string;
              description "Set string";
            }
          }

          container dhcpv6duid {
            description "Client DUID";
            leaf allowed-type {
              type uint32 {
                range "1..4";
              }
              description "Type of DUID to be allowed";
            }
          }

          container aaa-server {
            description "Enable aaa dhcpv6 option force-insert";

            container dhcpv6-option {
              description "Enable aaa dhcpv6 option force-insert";
              leaf force-insert {
                type empty;
                description "Enable aaa dhcpv6 option force-insert";
              }
            }
          }

          container options {
            description "DHCPv6 match";

            list option {
              key "type format value";
              description "DHCPv6 match option";

              container enterprise-id {
                description "match enterprise number";

                container hex-enterprise-id {
                  description "defaut action for enterprise number";
                  leaf action {
                    type Action;
                    description
                      "Configure Action to be take on match";
                  }
                }

                container default-enterprise-id {
                  description "defaut action for enterprise number";
                  leaf action {
                    type Action;
                    description
                      "Configure Action to be take on match";
                  }
                }
              }

              container vendor-class {
                description "match vendor class";

                container str-vendor-class {
                  description "string action for vendor number";
                  leaf action {
                    type Action;
                    description
                      "Configure Action to be take on match";
                  }
                }

                container default-vendor-class {
                  description
                    "default action for enterprise number";
                  leaf action {
                    type Action;
                    description
                      "Configure Action to be take on match";
                  }
                }
              }
              leaf type {
                type xr:Cisco-ios-xr-string;
                description "Set string";
              }
              leaf format {
                type uint32;
                description "Set constant integer";
              }
              leaf value {
                type xr:Cisco-ios-xr-string;
                description "Set string";
              }
            }
          }

          container dhcpv6-options {
            description "DHCPv6 options";

            container vendor-options {
              description "Vendor options";
              leaf type {
                type string;
                description "Set string";
              }
              leaf vendor-options {
                type string {
                  length "1..512";
                }
                description "Vendor options";
              }
            }
          }
          leaf address-pool {
            type string {
              length "1..64";
            }
            description "Address pool name";
          }
          leaf aftr-name {
            type xr:Cisco-ios-xr-string {
              length "1..64";
            }
            description "AFTR name";
          }
          leaf domain-name {
            type xr:Cisco-ios-xr-string {
              length "1..64";
            }
            description "Domain name";
          }
          leaf preference {
            type uint32 {
              range "0..255";
            }
            description "DHCP Server Preference";
          }
          leaf rapid-commit {
            type empty;
            description "Allow RAPID Commit";
          }
          leaf enable {
            type empty;
            mandatory true;
            description
              "Enable None. Deletion of this object also
              causes deletion of all associated objects
              under Server.";
          }
          leaf prefix-pool {
            type string {
              length "1..64";
            }
            description "Prefix pool name";
          }
        }
        leaf profile-name {
          type xr:Cisco-ios-xr-string;
          description "Profile name";
        }
      }
    }

    container interfaces {
      description "Table of Interface";

      list interface {
        key "interface-name";
        description "None";

        container pppoe {
          description "PPPoE subscriber interface";
          leaf profile {
            type xr:Cisco-ios-xr-string {
              length "1..64";
            }
            description "Enter profile name";
          }
        }

        container proxy {
          description "Assign a proxy profile to interface";
          leaf profile {
            type xr:Cisco-ios-xr-string {
              length "1..64";
            }
            description "Enter profile name";
          }
        }

        container base {
          description "Assign a base profile to interface";
          leaf profile {
            type xr:Cisco-ios-xr-string {
              length "1..64";
            }
            description "Enter profile name";
          }
        }

        container server {
          description "Assign a server profile to interface";
          leaf profile {
            type xr:Cisco-ios-xr-string {
              length "1..64";
            }
            description "Enter profile name";
          }
        }

        container relay {
          description "Assign a relay profile to interface";
          leaf profile {
            type xr:Cisco-ios-xr-string {
              length "1..64";
            }
            description "Enter profile name";
          }
        }
        leaf interface-name {
          type xr:Interface-name;
          description "Interface to configure";
        }
      }
    }
    leaf inner-cos {
      type uint32 {
        range "0..7";
      }
      description
        "Inner cos values for DHCPv6 packets to wards
        clients";
    }
    leaf enable {
      type empty;
      mandatory true;
      description
        "Enable None. Deletion of this object also causes
        deletion of all associated objects under DHCPv6.";
    }
    leaf allow-duid-change {
      type empty;
      description
        "For BNG session, allow duid change for a client
        MAC";
    }
    leaf outer-cos {
      type uint32 {
        range "0..7";
      }
      description
        "Configure outer cos values for DHCPv6 packet to
        wards client";
    }
  }
}
