submodule Cisco-IOS-XR-ocni-bgp-oper-sub1 {

  belongs-to Cisco-IOS-XR-ocni-bgp-oper {
    prefix Cisco-IOS-XR-ocni-bgp-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ocni-bgp package operational data.

     Copyright (c) 2013-2018 by Cisco Systems, Inc.
     All rights reserved.";

  revision "2015-11-09" {
    description
      "IOS XR 6.0 revision.";
  }

  typedef Openconfig-bgp-neighbor-mode-enum {
    type enumeration {
      enum helper-only {
        value 0;
        description
          "The local router is operating in helper-only
          mode, and hence will not retain forwarding
          state during a local session restart, but will
          do so during a restart of the remote peer";
      }
      enum bilateral {
        value 1;
        description
          "The local router is operating in both helper
          mode, and hence retains forwarding state during
          a remote restart, and also maintains forwarding
          state during local session restart";
      }
      enum remote-helper {
        value 2;
        description
          "The local system is able to retain routes
          during restart but the remote system is only
          able to act as a helper";
      }
    }
    description "Openconfig bgp neighbor mode enum";
  }
  typedef Openconfig-routing-policy-default-policy-type-enum {
    type enumeration {
      enum accept-route {
        value 0;
        description "default policy to accept the route";
      }
      enum reject-route {
        value 1;
        description "default policy to reject the route";
      }
    }
    description
      "Openconfig routing policy default policy type
      enum";
  }
  typedef Openconfig-bgp-neighbor-session-state-enum {
    type enumeration {
      enum idle {
        value 0;
        description
          "neighbor is down, and in the Idle state of the
          FSM";
      }
      enum connect {
        value 1;
        description
          "neighbor is down, and the session is waiting
          for the underlying transport session to be
          established";
      }
      enum active {
        value 2;
        description
          "neighbor is down, and the local system is
          awaiting a conncetion from the remote peer";
      }
      enum opensent {
        value 3;
        description
          "neighbor is in the process of being established
          . The local system has sent an OPEN message";
      }
      enum openconfirm {
        value 4;
        description
          "neighbor is in the process of being established
          . The local system is awaiting a NOTIFICATION
          or KEEPALIVE message";
      }
      enum established {
        value 5;
        description
          "neighbor is up - the BGP session with the peer
          is established";
      }
    }
    description "Openconfig bgp neighbor session state enum";
  }
  typedef Openconfig-bgp-types-community-type-enum {
    type enumeration {
      enum standard {
        value 0;
        description "Send only standard communities";
      }
      enum extended {
        value 1;
        description "Send only extended communities";
      }
      enum both {
        value 2;
        description "Send both standard and extended communities";
      }
      enum none {
        value 3;
        description "Do not send any community attribute";
      }
    }
    description "Openconfig bgp types community type enum";
  }
  typedef Openconfig-bgp-types-peer-type-enum {
    type enumeration {
      enum internal {
        value 0;
        description "Internal (iBGP) peer";
      }
      enum external {
        value 1;
        description "External (eBGP) peer";
      }
    }
    description "Openconfig bgp types peer type enum";
  }
  typedef Yang2bag-string {
    type string;
    description "Yang2bag string";
  }

  grouping PEER-GROUP-EBGP-MULTIHOP-STATE {
    description "PEER GROUP EBGP MULTIHOP STATE";
    leaf enabled {
      type boolean;
      description
        "When enabled the referenced group or neighbors
        are permitted to be indirectly connected -
        including cases where the TTL can be decremented
        between the BGP peers";
    }
    leaf multihop-ttl {
      type uint8;
      description
        "Time-to-live value to use when packets are sent
        to the referenced group or neighbors and
        ebgp-multihop is enabled";
    }
  }

  grouping OVERLAY-OCNI-BGP-PEER-GROUP-EBGP-MULTIHOP {
    description "eBGP multi-hop parameters for the BGPgroup";

    container state {
      description
        "State information for eBGP multihop, for the BGP
        neighbor or group";
      uses PEER-GROUP-EBGP-MULTIHOP-STATE;
    }
  }

  grouping PEER-GROUP-APPLY-POLICY-STATE {
    description "PEER GROUP APPLY POLICY STATE";
    leaf default-import-policy {
      type Openconfig-routing-policy-default-policy-type-enum;
      description
        "explicitly set a default policy if no policy
        definition in the import policy chain is
        satisfied";
    }
    leaf default-export-policy {
      type Openconfig-routing-policy-default-policy-type-enum;
      description
        "explicitly set a default policy if no policy
        definition in the export policy chain is
        satisfied";
    }
    leaf-list import-policy {
      type Yang2bag-string;
      description
        "list of policy names in sequence to be applied
        on receiving a routing update in the current
        context, e";
    }
    leaf-list export-policy {
      type Yang2bag-string;
      description
        "list of policy names in sequence to be applied
        on sending a routing update in the current
        context, e";
    }
  }

  grouping OVERLAY-OCNI-BGP-PEER-GROUP-APPLY-POLICY {
    description "Anchor point for routing policies in the model";

    container state {
      description "Operational state for routing policy";
      uses PEER-GROUP-APPLY-POLICY-STATE;
    }
  }

  grouping PEER-GROUP-ERROR-HANDLING-STATE {
    description "PEER GROUP ERROR HANDLING STATE";
    leaf treat-as-withdraw {
      type boolean;
      description
        "Specify whether erroneous UPDATE messages for
        which the NLRI can be extracted are reated as
        though the NLRI is withdrawn - avoiding session
        reset";
    }
  }

  grouping OVERLAY-OCNI-BGP-PEER-GROUP-ERROR-HANDLING {
    description
      "Error handling parameters used for the BGP
      peer-group";

    container state {
      description
        "State information relating to enhanced error
        handling mechanisms for the BGP group";
      uses PEER-GROUP-ERROR-HANDLING-STATE;
    }
  }

  grouping PEER-GROUP-GRACEFUL-RESTART-STATE {
    description "PEER GROUP GRACEFUL RESTART STATE";
    leaf enabled {
      type boolean;
      description
        "Enable or disable the graceful-restart
        capability";
    }
    leaf restart-time {
      type uint16;
      units "second";
      description
        "Estimated time (in seconds) for the local BGP
        speaker to restart a session";
    }
    leaf stale-routes-time {
      type Yang2bag-string;
      description
        "An upper-bound on the time thate stale routes
        will be retained by a router after a session is
        restarted";
    }
    leaf helper-only {
      type boolean;
      description "Enable graceful-restart in helper mode only";
    }
  }

  grouping OVERLAY-OCNI-BGP-PEER-GROUP-GRACEFUL-RESTART {
    description
      "Parameters relating the graceful restart
      mechanism for BGP";

    container state {
      description
        "State information associated with
        graceful-restart";
      uses PEER-GROUP-GRACEFUL-RESTART-STATE;
    }
  }

  grouping OVERLAY-OCNI-BGP-PEER-GROUP-STATE {
    description "State information relating to the BGP peer-group";
    leaf peer-group-name {
      type Yang2bag-string;
      description "Name of the BGP peer-group";
    }
    leaf peer-as {
      type uint32;
      description "AS number of the peer";
    }
    leaf local-as {
      type uint32;
      description
        "The local autonomous system number that is to be
        used when establishing sessions with the remote
        peer or peer group, if this differs from the
        global BGP router autonomous system number";
    }
    leaf peer-type {
      type Openconfig-bgp-types-peer-type-enum;
      description
        "Explicitly designate the peer or peer group as
        internal (iBGP) or external (eBGP)";
    }
    leaf auth-password {
      type Yang2bag-string;
      description
        "Configures an MD5 authentication password for
        use with neighboring devices";
    }
    leaf remove-private-as {
      type Yang2bag-string;
      description
        "Remove private AS numbers from updates sent to
        peers - when this leaf is not specified, the
        AS_PATH attribute should be sent to the peer
        unchanged";
    }
    leaf route-flap-damping {
      type boolean;
      description "Enable route flap damping";
    }
    leaf send-community {
      type Openconfig-bgp-types-community-type-enum;
      description
        "Specify which types of community should be sent
        to the neighbor or group";
    }
    leaf description {
      type Yang2bag-string;
      description
        "An optional textual description (intended
        primarily for use with a peer or group";
    }
    leaf total-paths {
      type uint32;
      description "Total number of BGP paths within the context";
    }
    leaf total-prefixes {
      type uint32;
      description
        "Total number of BGP prefixes received within the
        context";
    }
  }

  grouping AFI-SAFIS-AFI-SAFI-L2VPN-EVPN-PREFIX-LIMIT-STATE {
    description "AFI SAFIS AFI SAFI L2VPN EVPN PREFIX LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping AFI-SAFIS-AFI-SAFI-L2VPN-EVPN-PREFIX-LIMIT {
    description "AFI SAFIS AFI SAFI L2VPN EVPN PREFIX LIMIT";

    container state {
      description
        "State information relating to the prefix-limit
        for the AFI-SAFI";
      uses AFI-SAFIS-AFI-SAFI-L2VPN-EVPN-PREFIX-LIMIT-STATE;
    }
  }

  grouping AFI-SAFIS-AFI-SAFI-L2VPN-EVPN {
    description "AFI SAFIS AFI SAFI L2VPN EVPN";

    container prefix-limit {
      description
        "Configure the maximum number of prefixes that
        will be accepted from a peer";
      uses AFI-SAFIS-AFI-SAFI-L2VPN-EVPN-PREFIX-LIMIT;
    }
  }

  grouping AFI-SAFIS-AFI-SAFI-L2VPNVPLS-PREFIX-LIMIT-STATE {
    description "AFI SAFIS AFI SAFI L2VPNVPLS PREFIX LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping AFI-SAFIS-AFI-SAFI-L2VPNVPLS-PREFIX-LIMIT {
    description "AFI SAFIS AFI SAFI L2VPNVPLS PREFIX LIMIT";

    container state {
      description
        "State information relating to the prefix-limit
        for the AFI-SAFI";
      uses AFI-SAFIS-AFI-SAFI-L2VPNVPLS-PREFIX-LIMIT-STATE;
    }
  }

  grouping AFI-SAFIS-AFI-SAFI-L2VPNVPLS {
    description "AFI SAFIS AFI SAFI L2VPNVPLS";

    container prefix-limit {
      description
        "Configure the maximum number of prefixes that
        will be accepted from a peer";
      uses AFI-SAFIS-AFI-SAFI-L2VPNVPLS-PREFIX-LIMIT;
    }
  }

  grouping "AFI-SAFIS-AFI-SAFI-L3VPN-IPV6-MULTICAST-PREFIX-LIMIT"+
    "-STATE" {
    description
      "AFI SAFIS AFI SAFI L3VPN IPV6 MULTICAST PREFIX
      LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping AFI-SAFIS-AFI-SAFI-L3VPN-IPV6-MULTICAST-PREFIX-LIMIT {
    description
      "AFI SAFIS AFI SAFI L3VPN IPV6 MULTICAST PREFIX
      LIMIT";

    container state {
      description
        "State information relating to the prefix-limit
        for the AFI-SAFI";
      uses "AFI-SAFIS-AFI-SAFI-L3VPN-IPV6"+
        "-MULTICAST-PREFIX-LIMIT-STATE";
    }
  }

  grouping AFI-SAFIS-AFI-SAFI-L3VPN-IPV6-MULTICAST {
    description "AFI SAFIS AFI SAFI L3VPN IPV6 MULTICAST";

    container prefix-limit {
      description
        "Configure the maximum number of prefixes that
        will be accepted from a peer";
      uses AFI-SAFIS-AFI-SAFI-L3VPN-IPV6-MULTICAST-PREFIX-LIMIT;
    }
  }

  grouping "AFI-SAFIS-AFI-SAFI-L3VPN-IPV4-MULTICAST-PREFIX-LIMIT"+
    "-STATE" {
    description
      "AFI SAFIS AFI SAFI L3VPN IPV4 MULTICAST PREFIX
      LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping AFI-SAFIS-AFI-SAFI-L3VPN-IPV4-MULTICAST-PREFIX-LIMIT {
    description
      "AFI SAFIS AFI SAFI L3VPN IPV4 MULTICAST PREFIX
      LIMIT";

    container state {
      description
        "State information relating to the prefix-limit
        for the AFI-SAFI";
      uses "AFI-SAFIS-AFI-SAFI-L3VPN-IPV4"+
        "-MULTICAST-PREFIX-LIMIT-STATE";
    }
  }

  grouping AFI-SAFIS-AFI-SAFI-L3VPN-IPV4-MULTICAST {
    description "AFI SAFIS AFI SAFI L3VPN IPV4 MULTICAST";

    container prefix-limit {
      description
        "Configure the maximum number of prefixes that
        will be accepted from a peer";
      uses AFI-SAFIS-AFI-SAFI-L3VPN-IPV4-MULTICAST-PREFIX-LIMIT;
    }
  }

  grouping "AFI-SAFIS-AFI-SAFI-L3VPN-IPV6-UNICAST-PREFIX-LIMIT"+
    "-STATE" {
    description
      "AFI SAFIS AFI SAFI L3VPN IPV6 UNICAST PREFIX
      LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping AFI-SAFIS-AFI-SAFI-L3VPN-IPV6-UNICAST-PREFIX-LIMIT {
    description
      "AFI SAFIS AFI SAFI L3VPN IPV6 UNICAST PREFIX
      LIMIT";

    container state {
      description
        "State information relating to the prefix-limit
        for the AFI-SAFI";
      uses AFI-SAFIS-AFI-SAFI-L3VPN-IPV6-UNICAST-PREFIX-LIMIT-STATE;
    }
  }

  grouping AFI-SAFIS-AFI-SAFI-L3VPN-IPV6-UNICAST {
    description "AFI SAFIS AFI SAFI L3VPN IPV6 UNICAST";

    container prefix-limit {
      description
        "Configure the maximum number of prefixes that
        will be accepted from a peer";
      uses AFI-SAFIS-AFI-SAFI-L3VPN-IPV6-UNICAST-PREFIX-LIMIT;
    }
  }

  grouping "AFI-SAFIS-AFI-SAFI-L3VPN-IPV4-UNICAST-PREFIX-LIMIT"+
    "-STATE" {
    description
      "AFI SAFIS AFI SAFI L3VPN IPV4 UNICAST PREFIX
      LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping AFI-SAFIS-AFI-SAFI-L3VPN-IPV4-UNICAST-PREFIX-LIMIT {
    description
      "AFI SAFIS AFI SAFI L3VPN IPV4 UNICAST PREFIX
      LIMIT";

    container state {
      description
        "State information relating to the prefix-limit
        for the AFI-SAFI";
      uses AFI-SAFIS-AFI-SAFI-L3VPN-IPV4-UNICAST-PREFIX-LIMIT-STATE;
    }
  }

  grouping AFI-SAFIS-AFI-SAFI-L3VPN-IPV4-UNICAST {
    description "AFI SAFIS AFI SAFI L3VPN IPV4 UNICAST";

    container prefix-limit {
      description
        "Configure the maximum number of prefixes that
        will be accepted from a peer";
      uses AFI-SAFIS-AFI-SAFI-L3VPN-IPV4-UNICAST-PREFIX-LIMIT;
    }
  }

  grouping "AFI-SAFIS-AFI-SAFI-IPV6-LABELED-UNICAST-PREFIX-LIMIT"+
    "-STATE" {
    description
      "AFI SAFIS AFI SAFI IPV6 LABELED UNICAST PREFIX
      LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping AFI-SAFIS-AFI-SAFI-IPV6-LABELED-UNICAST-PREFIX-LIMIT {
    description
      "AFI SAFIS AFI SAFI IPV6 LABELED UNICAST PREFIX
      LIMIT";

    container state {
      description
        "State information relating to the prefix-limit
        for the AFI-SAFI";
      uses "AFI-SAFIS-AFI-SAFI-IPV6"+
        "-LABELED-UNICAST-PREFIX-LIMIT-STATE";
    }
  }

  grouping AFI-SAFIS-AFI-SAFI-IPV6-LABELED-UNICAST {
    description "AFI SAFIS AFI SAFI IPV6 LABELED UNICAST";

    container prefix-limit {
      description
        "Configure the maximum number of prefixes that
        will be accepted from a peer";
      uses AFI-SAFIS-AFI-SAFI-IPV6-LABELED-UNICAST-PREFIX-LIMIT;
    }
  }

  grouping "AFI-SAFIS-AFI-SAFI-IPV4-LABELED-UNICAST-PREFIX-LIMIT"+
    "-STATE" {
    description
      "AFI SAFIS AFI SAFI IPV4 LABELED UNICAST PREFIX
      LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping AFI-SAFIS-AFI-SAFI-IPV4-LABELED-UNICAST-PREFIX-LIMIT {
    description
      "AFI SAFIS AFI SAFI IPV4 LABELED UNICAST PREFIX
      LIMIT";

    container state {
      description
        "State information relating to the prefix-limit
        for the AFI-SAFI";
      uses "AFI-SAFIS-AFI-SAFI-IPV4"+
        "-LABELED-UNICAST-PREFIX-LIMIT-STATE";
    }
  }

  grouping AFI-SAFIS-AFI-SAFI-IPV4-LABELED-UNICAST {
    description "AFI SAFIS AFI SAFI IPV4 LABELED UNICAST";

    container prefix-limit {
      description
        "Configure the maximum number of prefixes that
        will be accepted from a peer";
      uses AFI-SAFIS-AFI-SAFI-IPV4-LABELED-UNICAST-PREFIX-LIMIT;
    }
  }

  grouping AFI-SAFIS-AFI-SAFI-IPV6-UNICAST-STATE {
    description "AFI SAFIS AFI SAFI IPV6 UNICAST STATE";
    leaf send-default-route {
      type boolean;
      description
        "If set to true, send the default-route to the
        neighbour(s)";
    }
  }

  grouping AFI-SAFIS-AFI-SAFI-IPV6-UNICAST-PREFIX-LIMIT-STATE {
    description
      "AFI SAFIS AFI SAFI IPV6 UNICAST PREFIX LIMIT
      STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping AFI-SAFIS-AFI-SAFI-IPV6-UNICAST-PREFIX-LIMIT {
    description "AFI SAFIS AFI SAFI IPV6 UNICAST PREFIX LIMIT";

    container state {
      description
        "State information relating to the prefix-limit
        for the AFI-SAFI";
      uses AFI-SAFIS-AFI-SAFI-IPV6-UNICAST-PREFIX-LIMIT-STATE;
    }
  }

  grouping AFI-SAFIS-AFI-SAFI-IPV6-UNICAST {
    description "AFI SAFIS AFI SAFI IPV6 UNICAST";

    container prefix-limit {
      description
        "Configure the maximum number of prefixes that
        will be accepted from a peer";
      uses AFI-SAFIS-AFI-SAFI-IPV6-UNICAST-PREFIX-LIMIT;
    }

    container state {
      description
        "State information for common IPv4 and IPv6
        unicast parameters";
      uses AFI-SAFIS-AFI-SAFI-IPV6-UNICAST-STATE;
    }
  }

  grouping AFI-SAFIS-AFI-SAFI-IPV4-UNICAST-STATE {
    description "AFI SAFIS AFI SAFI IPV4 UNICAST STATE";
    leaf send-default-route {
      type boolean;
      description
        "If set to true, send the default-route to the
        neighbour(s)";
    }
  }

  grouping AFI-SAFI-IPV4-UNICAST-PREFIX-LIMIT-STATE {
    description "AFI SAFI IPV4 UNICAST PREFIX LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping AFI-SAFI-IPV4-UNICAST-PREFIX-LIMIT {
    description "AFI SAFI IPV4 UNICAST PREFIX LIMIT";

    container state {
      description
        "State information relating to the prefix-limit
        for the AFI-SAFI";
      uses AFI-SAFI-IPV4-UNICAST-PREFIX-LIMIT-STATE;
    }
  }

  grouping AFI-SAFIS-AFI-SAFI-IPV4-UNICAST {
    description "AFI SAFIS AFI SAFI IPV4 UNICAST";

    container prefix-limit {
      description
        "Configure the maximum number of prefixes that
        will be accepted from a peer";
      uses AFI-SAFI-IPV4-UNICAST-PREFIX-LIMIT;
    }

    container state {
      description
        "State information for common IPv4 and IPv6
        unicast parameters";
      uses AFI-SAFIS-AFI-SAFI-IPV4-UNICAST-STATE;
    }
  }

  grouping AFI-SAFIS-AFI-SAFI-APPLY-POLICY-STATE {
    description "AFI SAFIS AFI SAFI APPLY POLICY STATE";
    leaf default-import-policy {
      type Openconfig-routing-policy-default-policy-type-enum;
      description
        "explicitly set a default policy if no policy
        definition in the import policy chain is
        satisfied";
    }
    leaf default-export-policy {
      type Openconfig-routing-policy-default-policy-type-enum;
      description
        "explicitly set a default policy if no policy
        definition in the export policy chain is
        satisfied";
    }
    leaf-list import-policy {
      type Yang2bag-string;
      description
        "list of policy names in sequence to be applied
        on receiving a routing update in the current
        context, e";
    }
    leaf-list export-policy {
      type Yang2bag-string;
      description
        "list of policy names in sequence to be applied
        on sending a routing update in the current
        context, e";
    }
  }

  grouping AFI-SAFI-APPLY-POLICY {
    description "AFI SAFI APPLY POLICY";

    container state {
      description "Operational state for routing policy";
      uses AFI-SAFIS-AFI-SAFI-APPLY-POLICY-STATE;
    }
  }

  grouping AFI-SAFI-USE-MULTIPLE-PATHS-IBGP-STATE {
    description "AFI SAFI USE MULTIPLE PATHS IBGP STATE";
    leaf maximum-paths {
      type uint32;
      description
        "Maximum number of parallel paths to consider
        when using iBGP multipath";
    }
  }

  grouping AFI-SAFI-USE-MULTIPLE-PATHS-IBGP {
    description "AFI SAFI USE MULTIPLE PATHS IBGP";

    container state {
      description "State information relating to iBGP multipath";
      uses AFI-SAFI-USE-MULTIPLE-PATHS-IBGP-STATE;
    }
  }

  grouping AFI-SAFIS-AFI-SAFI-USE-MULTIPLE-PATHS-EBGP-STATE {
    description "AFI SAFIS AFI SAFI USE MULTIPLE PATHS EBGP STATE";
    leaf allow-multiple-as {
      type boolean;
      description
        "Allow multipath to use paths from different
        neighbouring ASes";
    }
    leaf maximum-paths {
      type uint32;
      description
        "Maximum number of parallel paths to consider
        when using BGP multipath";
    }
  }

  grouping AFI-SAFIS-AFI-SAFI-USE-MULTIPLE-PATHS-EBGP {
    description "AFI SAFIS AFI SAFI USE MULTIPLE PATHS EBGP";

    container state {
      description "State information relating to eBGP multipath";
      uses AFI-SAFIS-AFI-SAFI-USE-MULTIPLE-PATHS-EBGP-STATE;
    }
  }

  grouping PEER-GROUP-AFI-SAFIS-AFI-SAFI-USE-MULTIPLE-PATHS-STATE {
    description
      "PEER GROUP AFI SAFIS AFI SAFI USE MULTIPLE PATHS
      STATE";
    leaf enabled {
      type boolean;
      description
        "Whether the use of multiple paths for the same
        NLRI is enabled for the neighbor";
    }
  }

  grouping AFI-SAFIS-AFI-SAFI-USE-MULTIPLE-PATHS {
    description "AFI SAFIS AFI SAFI USE MULTIPLE PATHS";

    container state {
      description "State parameters relating to multipath";
      uses PEER-GROUP-AFI-SAFIS-AFI-SAFI-USE-MULTIPLE-PATHS-STATE;
    }

    container ebgp {
      description "Multipath parameters for eBGP";
      uses AFI-SAFIS-AFI-SAFI-USE-MULTIPLE-PATHS-EBGP;
    }

    container ibgp {
      description "Multipath parameters for iBGP";
      uses AFI-SAFI-USE-MULTIPLE-PATHS-IBGP;
    }
  }

  grouping AFI-SAFIS-AFI-SAFI-ROUTE-SELECTION-OPTIONS-STATE {
    description "AFI SAFIS AFI SAFI ROUTE SELECTION OPTIONS STATE";
    leaf always-compare-med {
      type boolean;
      description
        "Compare multi-exit discriminator (MED) value
        from different ASes when selecting the best
        route";
    }
    leaf ignore-as-path-length {
      type boolean;
      description
        "Ignore the AS path length when selecting the
        best path";
    }
    leaf external-compare-router-id {
      type boolean;
      description
        "When comparing similar routes received from
        external BGP peers, use the router-id as a
        criterion to select the active path";
    }
    leaf advertise-inactive-routes {
      type boolean;
      description "Advertise inactive routes to external peers";
    }
    leaf enable-aigp {
      type boolean;
      description
        "Flag to enable sending / receiving accumulated
        IGP attribute in routing updates";
    }
    leaf ignore-next-hop-igp-metric {
      type boolean;
      description
        "Ignore the IGP metric to the next-hop when
        calculating BGP best-path";
    }
  }

  grouping AFI-SAFI-ROUTE-SELECTION-OPTIONS {
    description "AFI SAFI ROUTE SELECTION OPTIONS";

    container state {
      description
        "State information for the route selection
        options";
      uses AFI-SAFIS-AFI-SAFI-ROUTE-SELECTION-OPTIONS-STATE;
    }
  }

  grouping PEER-GROUP-AFI-SAFIS-AFI-SAFI-GRACEFUL-RESTART-STATE {
    description
      "PEER GROUP AFI SAFIS AFI SAFI GRACEFUL RESTART
      STATE";
    leaf enabled {
      type boolean;
      description
        "This leaf indicates whether graceful-restart is
        enabled for this AFI-SAFI";
    }
  }

  grouping AFI-SAFIS-AFI-SAFI-GRACEFUL-RESTART {
    description "AFI SAFIS AFI SAFI GRACEFUL RESTART";

    container state {
      description "State information for BGP graceful-restart";
      uses PEER-GROUP-AFI-SAFIS-AFI-SAFI-GRACEFUL-RESTART-STATE;
    }
  }

  grouping PEER-GROUP-AFI-SAFIS-AFI-SAFI-STATE {
    description "PEER GROUP AFI SAFIS AFI SAFI STATE";
    leaf afi-safi-name {
      type Yang2bag-string;
      description "AFI,SAFI";
    }
    leaf enabled {
      type boolean;
      description
        "This leaf indicates whether the IPv4 Unicast AFI
        ,SAFI is enabled for the neighbour or group";
    }
  }

  grouping OVERLAY-OCNI-BGP-PEER-GROUP-AFI-SAFIS-AFI-SAFI {
    description
      "AFI,SAFI configuration available for the
      neighbour or group";

    container state {
      description "State information relating to the AFI-SAFI";
      uses PEER-GROUP-AFI-SAFIS-AFI-SAFI-STATE;
    }

    container graceful-restart {
      description "Parameters relating to BGP graceful-restart";
      uses AFI-SAFIS-AFI-SAFI-GRACEFUL-RESTART;
    }

    container route-selection-options {
      description
        "Parameters relating to options for route
        selection";
      uses AFI-SAFI-ROUTE-SELECTION-OPTIONS;
    }

    container use-multiple-paths {
      description
        "Parameters related to the use of multiple paths
        for the same NLRI";
      uses AFI-SAFIS-AFI-SAFI-USE-MULTIPLE-PATHS;
    }

    container apply-policy {
      description "Anchor point for routing policies in the model";
      uses AFI-SAFI-APPLY-POLICY;
    }

    container ipv4-unicast {
      description "IPv4 unicast configuration options";
      uses AFI-SAFIS-AFI-SAFI-IPV4-UNICAST;
    }

    container ipv6-unicast {
      description "IPv6 unicast configuration options";
      uses AFI-SAFIS-AFI-SAFI-IPV6-UNICAST;
    }

    container ipv4-labeled-unicast {
      description "IPv4 Labeled Unicast configuration options";
      uses AFI-SAFIS-AFI-SAFI-IPV4-LABELED-UNICAST;
    }

    container ipv6-labeled-unicast {
      description "IPv6 Labeled Unicast configuration options";
      uses AFI-SAFIS-AFI-SAFI-IPV6-LABELED-UNICAST;
    }

    container l3vpn-ipv4-unicast {
      description "Unicast IPv4 L3VPN configuration options";
      uses AFI-SAFIS-AFI-SAFI-L3VPN-IPV4-UNICAST;
    }

    container l3vpn-ipv6-unicast {
      description "Unicast IPv6 L3VPN configuration options";
      uses AFI-SAFIS-AFI-SAFI-L3VPN-IPV6-UNICAST;
    }

    container l3vpn-ipv4-multicast {
      description "Multicast IPv4 L3VPN configuration options";
      uses AFI-SAFIS-AFI-SAFI-L3VPN-IPV4-MULTICAST;
    }

    container l3vpn-ipv6-multicast {
      description "Multicast IPv6 L3VPN configuration options";
      uses AFI-SAFIS-AFI-SAFI-L3VPN-IPV6-MULTICAST;
    }

    container l2vpnvpls {
      description "BGP-signalled VPLS configuration options";
      uses AFI-SAFIS-AFI-SAFI-L2VPNVPLS;
    }

    container l2vpn-evpn {
      description "BGP EVPN configuration options";
      uses AFI-SAFIS-AFI-SAFI-L2VPN-EVPN;
    }
  }

  grouping PEER-GROUP-AS-PATH-OPTIONS-STATE {
    description "PEER GROUP AS PATH OPTIONS STATE";
    leaf allow-own-as {
      type uint8;
      description
        "Specify the number of occurrences of the local
        BGP speaker's AS that can occur within the
        AS_PATH before it is rejected";
    }
    leaf replace-peer-as {
      type boolean;
      description
        "Replace occurrences of the peer's AS in the
        AS_PATH with the local autonomous system number";
    }
  }

  grouping OVERLAY-OCNI-BGP-PEER-GROUP-AS-PATH-OPTIONS {
    description
      "AS_PATH manipulation parameters for the BGP
      neighbor or group";

    container state {
      description
        "State information relating to the AS_PATH
        manipulation mechanisms for the BGP peer or
        group";
      uses PEER-GROUP-AS-PATH-OPTIONS-STATE;
    }
  }

  grouping PEER-GROUP-ADD-PATHS-STATE {
    description "PEER GROUP ADD PATHS STATE";
    leaf receive {
      type boolean;
      description
        "Enable ability to receive multiple path
        advertisements for an NLRI from the neighbor or
        group";
    }
    leaf send-max {
      type uint8;
      description
        "The maximum number of paths to advertise to
        neighbors for a single NLRI";
    }
    leaf eligible-prefix-policy {
      type Yang2bag-string;
      description
        "A reference to a routing policy which can be
        used to restrict the prefixes for which
        add-paths is enabled";
    }
  }

  grouping OVERLAY-OCNI-BGP-PEER-GROUP-ADD-PATHS {
    description
      "Parameters relating to the advertisement and
      receipt of multiple paths for a single NLRI
      (add-paths)";

    container state {
      description "State information associated with ADD_PATHS";
      uses PEER-GROUP-ADD-PATHS-STATE;
    }
  }

  grouping PEER-GROUP-LOGGING-OPTIONS-STATE {
    description "PEER GROUP LOGGING OPTIONS STATE";
    leaf log-neighbor-state-changes {
      type boolean;
      description "Configure logging of peer state changes";
    }
  }

  grouping OVERLAY-OCNI-BGP-PEER-GROUP-LOGGING-OPTIONS {
    description
      "Logging options for events related to the BGP
      neighbor or group";

    container state {
      description
        "State information relating to logging for the
        BGP neighbor or group";
      uses PEER-GROUP-LOGGING-OPTIONS-STATE;
    }
  }

  grouping PEER-GROUP-USE-MULTIPLE-PATHS-IBGP-STATE {
    description "PEER GROUP USE MULTIPLE PATHS IBGP STATE";
    leaf maximum-paths {
      type uint32;
      description
        "Maximum number of parallel paths to consider
        when using iBGP multipath";
    }
  }

  grouping PEER-GROUP-USE-MULTIPLE-PATHS-IBGP {
    description "PEER GROUP USE MULTIPLE PATHS IBGP";

    container state {
      description "State information relating to iBGP multipath";
      uses PEER-GROUP-USE-MULTIPLE-PATHS-IBGP-STATE;
    }
  }

  grouping PEER-GROUP-USE-MULTIPLE-PATHS-EBGP-STATE {
    description "PEER GROUP USE MULTIPLE PATHS EBGP STATE";
    leaf allow-multiple-as {
      type boolean;
      description
        "Allow multipath to use paths from different
        neighbouring ASes";
    }
    leaf maximum-paths {
      type uint32;
      description
        "Maximum number of parallel paths to consider
        when using BGP multipath";
    }
  }

  grouping PEER-GROUP-USE-MULTIPLE-PATHS-EBGP {
    description "PEER GROUP USE MULTIPLE PATHS EBGP";

    container state {
      description "State information relating to eBGP multipath";
      uses PEER-GROUP-USE-MULTIPLE-PATHS-EBGP-STATE;
    }
  }

  grouping PEER-GROUP-USE-MULTIPLE-PATHS-STATE {
    description "PEER GROUP USE MULTIPLE PATHS STATE";
    leaf enabled {
      type boolean;
      description
        "Whether the use of multiple paths for the same
        NLRI is enabled for the neighbor";
    }
  }

  grouping OVERLAY-OCNI-BGP-PEER-GROUP-USE-MULTIPLE-PATHS {
    description
      "Parameters related to the use of multiple paths
      for the same NLRI";

    container state {
      description "State parameters relating to multipath";
      uses PEER-GROUP-USE-MULTIPLE-PATHS-STATE;
    }

    container ebgp {
      description "Multipath parameters for eBGP";
      uses PEER-GROUP-USE-MULTIPLE-PATHS-EBGP;
    }

    container ibgp {
      description "Multipath parameters for iBGP";
      uses PEER-GROUP-USE-MULTIPLE-PATHS-IBGP;
    }
  }

  grouping PEER-GROUP-ROUTE-REFLECTOR-STATE {
    description "PEER GROUP ROUTE REFLECTOR STATE";
    leaf route-reflector-cluster-id {
      type Yang2bag-string;
      description
        "route-reflector cluster id to use when local
        router is configured as a route reflector";
    }
    leaf route-reflector-client {
      type boolean;
      description
        "Configure the neighbor as a route reflector
        client";
    }
  }

  grouping OVERLAY-OCNI-BGP-PEER-GROUP-ROUTE-REFLECTOR {
    description "Route reflector parameters for the BGPgroup";

    container state {
      description
        "State information relating to route reflection
        for the BGPgroup";
      uses PEER-GROUP-ROUTE-REFLECTOR-STATE;
    }
  }

  grouping PEER-GROUP-TIMERS-STATE {
    description "PEER GROUP TIMERS STATE";
    leaf connect-retry {
      type Yang2bag-string;
      units "second";
      description
        "Time interval in seconds between attempts to
        establish a session with the peer";
    }
    leaf hold-time {
      type Yang2bag-string;
      units "second";
      description
        "Time interval in seconds that a BGP session will
        be considered active in the absence of keepalive
        or other messages from the peer";
    }
    leaf keepalive-interval {
      type Yang2bag-string;
      units "second";
      description
        "Time interval in seconds between transmission of
        keepalive messages to the neighbor";
    }
    leaf minimum-advertisement-interval {
      type Yang2bag-string;
      description
        "Minimum time which must elapse between
        subsequent UPDATE messages relating to a common
        set of NLRI being transmitted to a peer";
    }
  }

  grouping OVERLAY-OCNI-BGP-PEER-GROUP-TIMERS {
    description "Timers related to a BGP peer-group";

    container state {
      description
        "State information relating to the timers used
        for the BGP group";
      uses PEER-GROUP-TIMERS-STATE;
    }
  }

  grouping PEER-GROUP-TRANSPORT-STATE {
    description "PEER GROUP TRANSPORT STATE";
    leaf tcp-mss {
      type uint16;
      description "Sets the max segment size for BGP TCP sessions";
    }
    leaf mtu-discovery {
      type boolean;
      description
        "Turns path mtu discovery for BGP TCP sessions on
        (true) or off (false)";
    }
    leaf passive-mode {
      type boolean;
      description
        "Wait for peers to issue requests to open a BGP
        session, rather than initiating sessions from
        the local router";
    }
    leaf local-address {
      type Yang2bag-string;
      description
        "Set the local IP (either IPv4 or IPv6) address
        to use for the session when sending BGP update
        messages";
    }
  }

  grouping OVERLAY-OCNI-BGP-PEER-GROUP-TRANSPORT {
    description
      "Transport session parameters for the BGP
      peer-group";

    container state {
      description
        "State information relating to the transport
        session(s) used for the BGP neighbor or group";
      uses PEER-GROUP-TRANSPORT-STATE;
    }
  }

  grouping EBGP-MULTIHOP-STATE {
    description "EBGP MULTIHOP STATE";
    leaf enabled {
      type boolean;
      description
        "When enabled the referenced group or neighbors
        are permitted to be indirectly connected -
        including cases where the TTL can be decremented
        between the BGP peers";
    }
    leaf multihop-ttl {
      type uint8;
      description
        "Time-to-live value to use when packets are sent
        to the referenced group or neighbors and
        ebgp-multihop is enabled";
    }
  }

  grouping OVERLAY-OCNI-BGP-EBGP-MULTIHOP {
    description "eBGP multi-hop parameters for the BGPgroup";

    container state {
      description
        "State information for eBGP multihop, for the BGP
        neighbor or group";
      uses EBGP-MULTIHOP-STATE;
    }
  }

  grouping ERROR-HANDLING-STATE {
    description "ERROR HANDLING STATE";
    leaf treat-as-withdraw {
      type boolean;
      description
        "Specify whether erroneous UPDATE messages for
        which the NLRI can be extracted are reated as
        though the NLRI is withdrawn - avoiding session
        reset";
    }
    leaf erroneous-update-messages {
      type uint32;
      description
        "The number of BGP UPDATE messages for which the
        treat-as-withdraw mechanism has been applied
        based on erroneous message contents";
    }
  }

  grouping OVERLAY-OCNI-BGP-ERROR-HANDLING {
    description
      "Error handling parameters used for the BGP
      neighbor or group";

    container state {
      description
        "State information relating to enhanced error
        handling mechanisms for the BGP neighbor";
      uses ERROR-HANDLING-STATE;
    }
  }

  grouping TIMERS-STATE {
    description "TIMERS STATE";
    leaf connect-retry {
      type Yang2bag-string;
      units "second";
      description
        "Time interval in seconds between attempts to
        establish a session with the peer";
    }
    leaf hold-time {
      type Yang2bag-string;
      units "second";
      description
        "Time interval in seconds that a BGP session will
        be considered active in the absence of keepalive
        or other messages from the peer";
    }
    leaf keepalive-interval {
      type Yang2bag-string;
      units "second";
      description
        "Time interval in seconds between transmission of
        keepalive messages to the neighbor";
    }
    leaf minimum-advertisement-interval {
      type Yang2bag-string;
      description
        "Minimum time which must elapse between
        subsequent UPDATE messages relating to a common
        set of NLRI being transmitted to a peer";
    }
    leaf negotiated-hold-time {
      type Yang2bag-string;
      description "The negotiated hold-time for the BGP session";
    }
  }

  grouping OVERLAY-OCNI-BGP-TIMERS {
    description "Timers related to a BGP neighbor";

    container state {
      description
        "State information relating to the timers used
        for the BGP neighbor";
      uses TIMERS-STATE;
    }
  }

  grouping AS-PATH-OPTIONS-STATE {
    description "AS PATH OPTIONS STATE";
    leaf allow-own-as {
      type uint8;
      description
        "Specify the number of occurrences of the local
        BGP speaker's AS that can occur within the
        AS_PATH before it is rejected";
    }
    leaf replace-peer-as {
      type boolean;
      description
        "Replace occurrences of the peer's AS in the
        AS_PATH with the local autonomous system number";
    }
  }

  grouping OVERLAY-OCNI-BGP-AS-PATH-OPTIONS {
    description
      "AS_PATH manipulation parameters for the BGP
      neighbor or group";

    container state {
      description
        "State information relating to the AS_PATH
        manipulation mechanisms for the BGP peer or
        group";
      uses AS-PATH-OPTIONS-STATE;
    }
  }

  grouping LOGGING-OPTIONS-STATE {
    description "LOGGING OPTIONS STATE";
    leaf log-neighbor-state-changes {
      type boolean;
      description "Configure logging of peer state changes";
    }
  }

  grouping OVERLAY-OCNI-BGP-LOGGING-OPTIONS {
    description
      "Logging options for events related to the BGP
      neighbor or group";

    container state {
      description
        "State information relating to logging for the
        BGP neighbor or group";
      uses LOGGING-OPTIONS-STATE;
    }
  }

  grouping TRANSPORT-STATE {
    description "TRANSPORT STATE";
    leaf tcp-mss {
      type uint16;
      description "Sets the max segment size for BGP TCP sessions";
    }
    leaf mtu-discovery {
      type boolean;
      description
        "Turns path mtu discovery for BGP TCP sessions on
        (true) or off (false)";
    }
    leaf passive-mode {
      type boolean;
      description
        "Wait for peers to issue requests to open a BGP
        session, rather than initiating sessions from
        the local router";
    }
    leaf local-address {
      type Yang2bag-string;
      description
        "Set the local IP (either IPv4 or IPv6) address
        to use for the session when sending BGP update
        messages";
    }
    leaf local-port {
      type uint16;
      description
        "Local TCP port being used for the TCP session
        supporting the BGP session";
    }
    leaf remote-address {
      type Yang2bag-string;
      description
        "Remote address to which the BGP session has been
        established";
    }
    leaf remote-port {
      type uint16;
      description
        "Remote port being used by the peer for the TCP
        session supporting the BGP session";
    }
  }

  grouping OVERLAY-OCNI-BGP-TRANSPORT {
    description "Transport session parameters for the BGP neighbor";

    container state {
      description
        "State information relating to the transport
        session(s) used for the BGP neighbor";
      uses TRANSPORT-STATE;
    }
  }

  grouping ADD-PATHS-STATE {
    description "ADD PATHS STATE";
    leaf receive {
      type boolean;
      description
        "Enable ability to receive multiple path
        advertisements for an NLRI from the neighbor or
        group";
    }
    leaf send-max {
      type uint8;
      description
        "The maximum number of paths to advertise to
        neighbors for a single NLRI";
    }
    leaf eligible-prefix-policy {
      type Yang2bag-string;
      description
        "A reference to a routing policy which can be
        used to restrict the prefixes for which
        add-paths is enabled";
    }
  }

  grouping OVERLAY-OCNI-BGP-ADD-PATHS {
    description
      "Parameters relating to the advertisement and
      receipt of multiple paths for a single NLRI
      (add-paths)";

    container state {
      description "State information associated with ADD_PATHS";
      uses ADD-PATHS-STATE;
    }
  }

  grouping APPLY-POLICY-STATE {
    description "APPLY POLICY STATE";
    leaf default-import-policy {
      type Openconfig-routing-policy-default-policy-type-enum;
      description
        "explicitly set a default policy if no policy
        definition in the import policy chain is
        satisfied";
    }
    leaf default-export-policy {
      type Openconfig-routing-policy-default-policy-type-enum;
      description
        "explicitly set a default policy if no policy
        definition in the export policy chain is
        satisfied";
    }
    leaf-list import-policy {
      type Yang2bag-string;
      description
        "list of policy names in sequence to be applied
        on receiving a routing update in the current
        context, e";
    }
    leaf-list export-policy {
      type Yang2bag-string;
      description
        "list of policy names in sequence to be applied
        on sending a routing update in the current
        context, e";
    }
  }

  grouping OVERLAY-OCNI-BGP-APPLY-POLICY {
    description "Anchor point for routing policies in the model";

    container state {
      description "Operational state for routing policy";
      uses APPLY-POLICY-STATE;
    }
  }

  grouping ROUTE-REFLECTOR-STATE {
    description "ROUTE REFLECTOR STATE";
    leaf route-reflector-cluster-id {
      type Yang2bag-string;
      description
        "route-reflector cluster id to use when local
        router is configured as a route reflector";
    }
    leaf route-reflector-client {
      type boolean;
      description
        "Configure the neighbor as a route reflector
        client";
    }
  }

  grouping OVERLAY-OCNI-BGP-ROUTE-REFLECTOR {
    description "Route reflector parameters for the BGPgroup";

    container state {
      description
        "State information relating to route reflection
        for the BGPgroup";
      uses ROUTE-REFLECTOR-STATE;
    }
  }

  grouping NEIGHBOR-GRACEFUL-RESTART-STATE {
    description "NEIGHBOR GRACEFUL RESTART STATE";
    leaf enabled {
      type boolean;
      description
        "Enable or disable the graceful-restart
        capability";
    }
    leaf restart-time {
      type uint16;
      units "second";
      description
        "Estimated time (in seconds) for the local BGP
        speaker to restart a session";
    }
    leaf stale-routes-time {
      type Yang2bag-string;
      description
        "An upper-bound on the time thate stale routes
        will be retained by a router after a session is
        restarted";
    }
    leaf helper-only {
      type boolean;
      description "Enable graceful-restart in helper mode only";
    }
    leaf peer-restart-time {
      type uint16;
      description
        "The period of time (advertised by the peer) that
        the peer expects a restart of a BGP session to
        take";
    }
    leaf peer-restarting {
      type boolean;
      description
        "This flag indicates whether the remote neighbor
        is currently in the process of restarting, and
        hence received routes are currently stale";
    }
    leaf local-restarting {
      type boolean;
      description
        "This flag indicates whether the local neighbor
        is currently restarting";
    }
    leaf mode {
      type Openconfig-bgp-neighbor-mode-enum;
      description
        "Ths leaf indicates the mode of operation of BGP
        graceful restart with the peer";
    }
  }

  grouping OVERLAY-OCNI-BGP-NEIGHBOR-GRACEFUL-RESTART {
    description
      "Parameters relating the graceful restart
      mechanism for BGP";

    container state {
      description
        "State information associated with
        graceful-restart";
      uses NEIGHBOR-GRACEFUL-RESTART-STATE;
    }
  }

  grouping AFI-SAFI-USE-MULTIPLE-PATHS-EBGP-STATE {
    description "AFI SAFI USE MULTIPLE PATHS EBGP STATE";
    leaf allow-multiple-as {
      type boolean;
      description
        "Allow multipath to use paths from different
        neighbouring ASes";
    }
  }

  grouping AFI-SAFI-USE-MULTIPLE-PATHS-EBGP {
    description "AFI SAFI USE MULTIPLE PATHS EBGP";

    container state {
      description "State information relating to eBGP multipath";
      uses AFI-SAFI-USE-MULTIPLE-PATHS-EBGP-STATE;
    }
  }

  grouping AFI-SAFIS-AFI-SAFI-USE-MULTIPLE-PATHS-STATE {
    description "AFI SAFIS AFI SAFI USE MULTIPLE PATHS STATE";
    leaf enabled {
      type boolean;
      description
        "Whether the use of multiple paths for the same
        NLRI is enabled for the neighbor";
    }
  }

  grouping AFI-SAFI-USE-MULTIPLE-PATHS {
    description "AFI SAFI USE MULTIPLE PATHS";

    container state {
      description "State parameters relating to multipath";
      uses AFI-SAFIS-AFI-SAFI-USE-MULTIPLE-PATHS-STATE;
    }

    container ebgp {
      description "Multipath configuration for eBGP";
      uses AFI-SAFI-USE-MULTIPLE-PATHS-EBGP;
    }
  }

  grouping AFI-SAFI-L2VPN-EVPN-PREFIX-LIMIT-STATE {
    description "AFI SAFI L2VPN EVPN PREFIX LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping AFI-SAFI-L2VPN-EVPN-PREFIX-LIMIT {
    description "AFI SAFI L2VPN EVPN PREFIX LIMIT";

    container state {
      description
        "State information relating to the prefix-limit
        for the AFI-SAFI";
      uses AFI-SAFI-L2VPN-EVPN-PREFIX-LIMIT-STATE;
    }
  }

  grouping AFI-SAFI-L2VPN-EVPN {
    description "AFI SAFI L2VPN EVPN";

    container prefix-limit {
      description
        "Configure the maximum number of prefixes that
        will be accepted from a peer";
      uses AFI-SAFI-L2VPN-EVPN-PREFIX-LIMIT;
    }
  }

  grouping AFI-SAFI-L2VPNVPLS-PREFIX-LIMIT-STATE {
    description "AFI SAFI L2VPNVPLS PREFIX LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping AFI-SAFI-L2VPNVPLS-PREFIX-LIMIT {
    description "AFI SAFI L2VPNVPLS PREFIX LIMIT";

    container state {
      description
        "State information relating to the prefix-limit
        for the AFI-SAFI";
      uses AFI-SAFI-L2VPNVPLS-PREFIX-LIMIT-STATE;
    }
  }

  grouping AFI-SAFI-L2VPNVPLS {
    description "AFI SAFI L2VPNVPLS";

    container prefix-limit {
      description
        "Configure the maximum number of prefixes that
        will be accepted from a peer";
      uses AFI-SAFI-L2VPNVPLS-PREFIX-LIMIT;
    }
  }

  grouping AFI-SAFI-L3VPN-IPV6-MULTICAST-PREFIX-LIMIT-STATE {
    description "AFI SAFI L3VPN IPV6 MULTICAST PREFIX LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping AFI-SAFI-L3VPN-IPV6-MULTICAST-PREFIX-LIMIT {
    description "AFI SAFI L3VPN IPV6 MULTICAST PREFIX LIMIT";

    container state {
      description
        "State information relating to the prefix-limit
        for the AFI-SAFI";
      uses AFI-SAFI-L3VPN-IPV6-MULTICAST-PREFIX-LIMIT-STATE;
    }
  }

  grouping AFI-SAFI-L3VPN-IPV6-MULTICAST {
    description "AFI SAFI L3VPN IPV6 MULTICAST";

    container prefix-limit {
      description
        "Configure the maximum number of prefixes that
        will be accepted from a peer";
      uses AFI-SAFI-L3VPN-IPV6-MULTICAST-PREFIX-LIMIT;
    }
  }

  grouping AFI-SAFI-L3VPN-IPV4-MULTICAST-PREFIX-LIMIT-STATE {
    description "AFI SAFI L3VPN IPV4 MULTICAST PREFIX LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping AFI-SAFI-L3VPN-IPV4-MULTICAST-PREFIX-LIMIT {
    description "AFI SAFI L3VPN IPV4 MULTICAST PREFIX LIMIT";

    container state {
      description
        "State information relating to the prefix-limit
        for the AFI-SAFI";
      uses AFI-SAFI-L3VPN-IPV4-MULTICAST-PREFIX-LIMIT-STATE;
    }
  }

  grouping AFI-SAFI-L3VPN-IPV4-MULTICAST {
    description "AFI SAFI L3VPN IPV4 MULTICAST";

    container prefix-limit {
      description
        "Configure the maximum number of prefixes that
        will be accepted from a peer";
      uses AFI-SAFI-L3VPN-IPV4-MULTICAST-PREFIX-LIMIT;
    }
  }

  grouping AFI-SAFI-L3VPN-IPV6-UNICAST-PREFIX-LIMIT-STATE {
    description "AFI SAFI L3VPN IPV6 UNICAST PREFIX LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping AFI-SAFI-L3VPN-IPV6-UNICAST-PREFIX-LIMIT {
    description "AFI SAFI L3VPN IPV6 UNICAST PREFIX LIMIT";

    container state {
      description
        "State information relating to the prefix-limit
        for the AFI-SAFI";
      uses AFI-SAFI-L3VPN-IPV6-UNICAST-PREFIX-LIMIT-STATE;
    }
  }

  grouping AFI-SAFI-L3VPN-IPV6-UNICAST {
    description "AFI SAFI L3VPN IPV6 UNICAST";

    container prefix-limit {
      description
        "Configure the maximum number of prefixes that
        will be accepted from a peer";
      uses AFI-SAFI-L3VPN-IPV6-UNICAST-PREFIX-LIMIT;
    }
  }

  grouping AFI-SAFI-L3VPN-IPV4-UNICAST-PREFIX-LIMIT-STATE {
    description "AFI SAFI L3VPN IPV4 UNICAST PREFIX LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping AFI-SAFI-L3VPN-IPV4-UNICAST-PREFIX-LIMIT {
    description "AFI SAFI L3VPN IPV4 UNICAST PREFIX LIMIT";

    container state {
      description
        "State information relating to the prefix-limit
        for the AFI-SAFI";
      uses AFI-SAFI-L3VPN-IPV4-UNICAST-PREFIX-LIMIT-STATE;
    }
  }

  grouping AFI-SAFI-L3VPN-IPV4-UNICAST {
    description "AFI SAFI L3VPN IPV4 UNICAST";

    container prefix-limit {
      description
        "Configure the maximum number of prefixes that
        will be accepted from a peer";
      uses AFI-SAFI-L3VPN-IPV4-UNICAST-PREFIX-LIMIT;
    }
  }

  grouping AFI-SAFI-IPV6-LABELED-UNICAST-PREFIX-LIMIT-STATE {
    description "AFI SAFI IPV6 LABELED UNICAST PREFIX LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping AFI-SAFI-IPV6-LABELED-UNICAST-PREFIX-LIMIT {
    description "AFI SAFI IPV6 LABELED UNICAST PREFIX LIMIT";

    container state {
      description
        "State information relating to the prefix-limit
        for the AFI-SAFI";
      uses AFI-SAFI-IPV6-LABELED-UNICAST-PREFIX-LIMIT-STATE;
    }
  }

  grouping AFI-SAFI-IPV6-LABELED-UNICAST {
    description "AFI SAFI IPV6 LABELED UNICAST";

    container prefix-limit {
      description
        "Configure the maximum number of prefixes that
        will be accepted from a peer";
      uses AFI-SAFI-IPV6-LABELED-UNICAST-PREFIX-LIMIT;
    }
  }

  grouping AFI-SAFI-IPV4-LABELED-UNICAST-PREFIX-LIMIT-STATE {
    description "AFI SAFI IPV4 LABELED UNICAST PREFIX LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping AFI-SAFI-IPV4-LABELED-UNICAST-PREFIX-LIMIT {
    description "AFI SAFI IPV4 LABELED UNICAST PREFIX LIMIT";

    container state {
      description
        "State information relating to the prefix-limit
        for the AFI-SAFI";
      uses AFI-SAFI-IPV4-LABELED-UNICAST-PREFIX-LIMIT-STATE;
    }
  }

  grouping AFI-SAFI-IPV4-LABELED-UNICAST {
    description "AFI SAFI IPV4 LABELED UNICAST";

    container prefix-limit {
      description
        "Configure the maximum number of prefixes that
        will be accepted from a peer";
      uses AFI-SAFI-IPV4-LABELED-UNICAST-PREFIX-LIMIT;
    }
  }

  grouping AFI-SAFI-IPV6-UNICAST-STATE {
    description "AFI SAFI IPV6 UNICAST STATE";
    leaf send-default-route {
      type boolean;
      description
        "If set to true, send the default-route to the
        neighbour(s)";
    }
  }

  grouping AFI-SAFI-IPV6-UNICAST-PREFIX-LIMIT-STATE {
    description "AFI SAFI IPV6 UNICAST PREFIX LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping AFI-SAFI-IPV6-UNICAST-PREFIX-LIMIT {
    description "AFI SAFI IPV6 UNICAST PREFIX LIMIT";

    container state {
      description
        "State information relating to the prefix-limit
        for the AFI-SAFI";
      uses AFI-SAFI-IPV6-UNICAST-PREFIX-LIMIT-STATE;
    }
  }

  grouping AFI-SAFI-IPV6-UNICAST {
    description "AFI SAFI IPV6 UNICAST";

    container prefix-limit {
      description
        "Configure the maximum number of prefixes that
        will be accepted from a peer";
      uses AFI-SAFI-IPV6-UNICAST-PREFIX-LIMIT;
    }

    container state {
      description
        "State information for common IPv4 and IPv6
        unicast parameters";
      uses AFI-SAFI-IPV6-UNICAST-STATE;
    }
  }

  grouping AFI-SAFI-IPV4-UNICAST-STATE {
    description "AFI SAFI IPV4 UNICAST STATE";
    leaf send-default-route {
      type boolean;
      description
        "If set to true, send the default-route to the
        neighbour(s)";
    }
  }

  grouping IPV4-UNICAST-PREFIX-LIMIT-STATE {
    description "IPV4 UNICAST PREFIX LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping IPV4-UNICAST-PREFIX-LIMIT {
    description "IPV4 UNICAST PREFIX LIMIT";

    container state {
      description
        "State information relating to the prefix-limit
        for the AFI-SAFI";
      uses IPV4-UNICAST-PREFIX-LIMIT-STATE;
    }
  }

  grouping AFI-SAFI-IPV4-UNICAST {
    description "AFI SAFI IPV4 UNICAST";

    container prefix-limit {
      description
        "Configure the maximum number of prefixes that
        will be accepted from a peer";
      uses IPV4-UNICAST-PREFIX-LIMIT;
    }

    container state {
      description
        "State information for common IPv4 and IPv6
        unicast parameters";
      uses AFI-SAFI-IPV4-UNICAST-STATE;
    }
  }

  grouping AFI-SAFI-APPLY-POLICY-STATE {
    description "AFI SAFI APPLY POLICY STATE";
    leaf default-import-policy {
      type Openconfig-routing-policy-default-policy-type-enum;
      description
        "explicitly set a default policy if no policy
        definition in the import policy chain is
        satisfied";
    }
    leaf default-export-policy {
      type Openconfig-routing-policy-default-policy-type-enum;
      description
        "explicitly set a default policy if no policy
        definition in the export policy chain is
        satisfied";
    }
    leaf-list import-policy {
      type Yang2bag-string;
      description
        "list of policy names in sequence to be applied
        on receiving a routing update in the current
        context, e";
    }
    leaf-list export-policy {
      type Yang2bag-string;
      description
        "list of policy names in sequence to be applied
        on sending a routing update in the current
        context, e";
    }
  }

  grouping APPLY-POLICY {
    description "APPLY POLICY";

    container state {
      description "Operational state for routing policy";
      uses AFI-SAFI-APPLY-POLICY-STATE;
    }
  }

  grouping AFI-SAFIS-AFI-SAFI-GRACEFUL-RESTART-STATE {
    description "AFI SAFIS AFI SAFI GRACEFUL RESTART STATE";
    leaf enabled {
      type boolean;
      description
        "This leaf indicates whether graceful-restart is
        enabled for this AFI-SAFI";
    }
    leaf received {
      type boolean;
      description
        "This leaf indicates whether the neighbor
        advertised the ability to support
        graceful-restart for this AFI-SAFI";
    }
    leaf advertised {
      type boolean;
      description
        "This leaf indicates whether the ability to
        support graceful-restart has been advertised to
        the peer";
    }
  }

  grouping AFI-SAFI-GRACEFUL-RESTART {
    description "AFI SAFI GRACEFUL RESTART";

    container state {
      description "State information for BGP graceful-restart";
      uses AFI-SAFIS-AFI-SAFI-GRACEFUL-RESTART-STATE;
    }
  }

  grouping PREFIXES {
    description "PREFIXES";
    leaf received {
      type uint32;
      description
        "The number of prefixes received from the
        neighbor";
    }
    leaf sent {
      type uint32;
      description
        "The number of prefixes advertised to the
        neighbor";
    }
    leaf installed {
      type uint32;
      description
        "The number of advertised prefixes installed in
        the Loc-RIB";
    }
  }

  grouping AFI-SAFIS-AFI-SAFI-STATE {
    description "AFI SAFIS AFI SAFI STATE";

    container prefixes {
      description "Prefix counters for the BGP session";
      uses PREFIXES;
    }
    leaf afi-safi-name {
      type Yang2bag-string;
      description "AFI,SAFI";
    }
    leaf enabled {
      type boolean;
      description
        "This leaf indicates whether the IPv4 Unicast AFI
        ,SAFI is enabled for the neighbour or group";
    }
    leaf active {
      type boolean;
      description
        "This value indicates whether a particular
        AFI-SAFI has been succesfully negotiated with
        the peer";
    }
  }

  grouping OVERLAY-OCNI-BGP-AFI-SAFIS-AFI-SAFI {
    description
      "AFI,SAFI configuration available for the
      neighbour or group";

    container state {
      description "State information relating to the AFI-SAFI";
      uses AFI-SAFIS-AFI-SAFI-STATE;
    }

    container graceful-restart {
      description "Parameters relating to BGP graceful-restart";
      uses AFI-SAFI-GRACEFUL-RESTART;
    }

    container apply-policy {
      description "Anchor point for routing policies in the model";
      uses APPLY-POLICY;
    }

    container ipv4-unicast {
      description "IPv4 unicast configuration options";
      uses AFI-SAFI-IPV4-UNICAST;
    }

    container ipv6-unicast {
      description "IPv6 unicast configuration options";
      uses AFI-SAFI-IPV6-UNICAST;
    }

    container ipv4-labeled-unicast {
      description "IPv4 Labeled Unicast configuration options";
      uses AFI-SAFI-IPV4-LABELED-UNICAST;
    }

    container ipv6-labeled-unicast {
      description "IPv6 Labeled Unicast configuration options";
      uses AFI-SAFI-IPV6-LABELED-UNICAST;
    }

    container l3vpn-ipv4-unicast {
      description "Unicast IPv4 L3VPN configuration options";
      uses AFI-SAFI-L3VPN-IPV4-UNICAST;
    }

    container l3vpn-ipv6-unicast {
      description "Unicast IPv6 L3VPN configuration options";
      uses AFI-SAFI-L3VPN-IPV6-UNICAST;
    }

    container l3vpn-ipv4-multicast {
      description "Multicast IPv4 L3VPN configuration options";
      uses AFI-SAFI-L3VPN-IPV4-MULTICAST;
    }

    container l3vpn-ipv6-multicast {
      description "Multicast IPv6 L3VPN configuration options";
      uses AFI-SAFI-L3VPN-IPV6-MULTICAST;
    }

    container l2vpnvpls {
      description "BGP-signalled VPLS configuration options";
      uses AFI-SAFI-L2VPNVPLS;
    }

    container l2vpn-evpn {
      description "BGP EVPN configuration options";
      uses AFI-SAFI-L2VPN-EVPN;
    }

    container use-multiple-paths {
      description
        "Parameters related to the use of multiple-paths
        for the same NLRI when they are received only
        from this neighbor";
      uses AFI-SAFI-USE-MULTIPLE-PATHS;
    }
  }

  grouping NEIGHBOR-USE-MULTIPLE-PATHS-EBGP-STATE {
    description "NEIGHBOR USE MULTIPLE PATHS EBGP STATE";
    leaf allow-multiple-as {
      type boolean;
      description
        "Allow multipath to use paths from different
        neighbouring ASes";
    }
  }

  grouping NEIGHBOR-USE-MULTIPLE-PATHS-EBGP {
    description "NEIGHBOR USE MULTIPLE PATHS EBGP";

    container state {
      description "State information relating to eBGP multipath";
      uses NEIGHBOR-USE-MULTIPLE-PATHS-EBGP-STATE;
    }
  }

  grouping NEIGHBOR-USE-MULTIPLE-PATHS-STATE {
    description "NEIGHBOR USE MULTIPLE PATHS STATE";
    leaf enabled {
      type boolean;
      description
        "Whether the use of multiple paths for the same
        NLRI is enabled for the neighbor";
    }
  }

  grouping OVERLAY-OCNI-BGP-NEIGHBOR-USE-MULTIPLE-PATHS {
    description
      "Parameters related to the use of multiple-paths
      for the same NLRI when they are received only
      from this neighbor";

    container state {
      description "State parameters relating to multipath";
      uses NEIGHBOR-USE-MULTIPLE-PATHS-STATE;
    }

    container ebgp {
      description "Multipath configuration for eBGP";
      uses NEIGHBOR-USE-MULTIPLE-PATHS-EBGP;
    }
  }

  grouping QUEUES {
    description "QUEUES";
    leaf input {
      type uint32;
      description
        "The number of messages received from the peer
        currently queued";
    }
    leaf output {
      type uint32;
      description
        "The number of messages queued to be sent to the
        peer";
    }
  }

  grouping RECEIVED {
    description "RECEIVED";
    leaf update {
      type uint64;
      description
        "Number of BGP UPDATE messages announcing,
        withdrawing or modifying paths exchanged";
    }
    leaf notification {
      type uint64;
      description
        "Number of BGP NOTIFICATION messages indicating
        an error condition has occurred exchanged";
    }
  }

  grouping SENT {
    description "SENT";
    leaf update {
      type uint64;
      description
        "Number of BGP UPDATE messages announcing,
        withdrawing or modifying paths exchanged";
    }
    leaf notification {
      type uint64;
      description
        "Number of BGP NOTIFICATION messages indicating
        an error condition has occurred exchanged";
    }
  }

  grouping MESSAGES {
    description "MESSAGES";

    container sent {
      description
        "Counters relating to BGP messages sent to the
        neighbor";
      uses SENT;
    }

    container received {
      description
        "Counters for BGP messages received from the
        neighbor";
      uses RECEIVED;
    }
  }

  grouping OVERLAY-OCNI-BGP-NEIGHBOR-STATE {
    description "State information relating to the BGP neighbor";

    container messages {
      description
        "Counters for BGP messages sent and received from
        the neighbor";
      uses MESSAGES;
    }

    container queues {
      description
        "Counters related to queued messages associated
        with the BGP neighbor";
      uses QUEUES;
    }
    leaf peer-group {
      type Yang2bag-string;
      description
        "The peer-group with which this neighbor is
        associated";
    }
    leaf neighbor-address {
      type Yang2bag-string;
      description "Address of the BGP peer, either in IPv4 or IPv6";
    }
    leaf enabled {
      type boolean;
      description "Whether the BGP peer is enabled";
    }
    leaf peer-as {
      type uint32;
      description "AS number of the peer";
    }
    leaf local-as {
      type uint32;
      description
        "The local autonomous system number that is to be
        used when establishing sessions with the remote
        peer or peer group, if this differs from the
        global BGP router autonomous system number";
    }
    leaf peer-type {
      type Openconfig-bgp-types-peer-type-enum;
      description
        "Explicitly designate the peer or peer group as
        internal (iBGP) or external (eBGP)";
    }
    leaf auth-password {
      type Yang2bag-string;
      description
        "Configures an MD5 authentication password for
        use with neighboring devices";
    }
    leaf remove-private-as {
      type Yang2bag-string;
      description
        "Remove private AS numbers from updates sent to
        peers - when this leaf is not specified, the
        AS_PATH attribute should be sent to the peer
        unchanged";
    }
    leaf route-flap-damping {
      type boolean;
      description "Enable route flap damping";
    }
    leaf send-community {
      type Openconfig-bgp-types-community-type-enum;
      description
        "Specify which types of community should be sent
        to the neighbor or group";
    }
    leaf description {
      type Yang2bag-string;
      description
        "An optional textual description (intended
        primarily for use with a peer or group";
    }
    leaf session-state {
      type Openconfig-bgp-neighbor-session-state-enum;
      description "Operational state of the BGP peer";
    }
    leaf last-established {
      type uint64;
      description
        "This timestamp indicates the time that the BGP
        session last transitioned in or out of the
        Established state";
    }
    leaf established-transitions {
      type uint64;
      description
        "Number of transitions to the Established state
        for the neighbor session";
    }
    leaf dynamically-configured {
      type boolean;
      description
        "When this leaf is set to true, the peer was
        configured dynamically due to an inbound
        connection request from a specified source
        prefix within a dynamic-neighbor-prefix";
    }
    leaf-list supported-capability {
      type Yang2bag-string;
      description
        "BGP capabilities negotiated as supported with
        the peer";
    }
  }

  grouping ROUTE-SELECTION-OPTIONS-STATE {
    description "ROUTE SELECTION OPTIONS STATE";
    leaf always-compare-med {
      type boolean;
      description
        "Compare multi-exit discriminator (MED) value
        from different ASes when selecting the best
        route";
    }
    leaf ignore-as-path-length {
      type boolean;
      description
        "Ignore the AS path length when selecting the
        best path";
    }
    leaf external-compare-router-id {
      type boolean;
      description
        "When comparing similar routes received from
        external BGP peers, use the router-id as a
        criterion to select the active path";
    }
    leaf advertise-inactive-routes {
      type boolean;
      description "Advertise inactive routes to external peers";
    }
    leaf enable-aigp {
      type boolean;
      description
        "Flag to enable sending / receiving accumulated
        IGP attribute in routing updates";
    }
    leaf ignore-next-hop-igp-metric {
      type boolean;
      description
        "Ignore the IGP metric to the next-hop when
        calculating BGP best-path";
    }
  }

  grouping OVERLAY-OCNI-BGP-ROUTE-SELECTION-OPTIONS {
    description
      "Parameters relating to options for route
      selection";

    container state {
      description
        "State information for the route selection
        options";
      uses ROUTE-SELECTION-OPTIONS-STATE;
    }
  }

  grouping DYNAMIC-NEIGHBOR-PREFIX-STATE {
    description "DYNAMIC NEIGHBOR PREFIX STATE";
    leaf prefix {
      type Yang2bag-string;
      description
        "The IP prefix within which the source address of
        the remote BGP speaker must fall to be
        considered eligible to the dynamically
        configured";
    }
    leaf peer-group {
      type Yang2bag-string;
      description
        "The peer-group within which the dynamic neighbor
        will be configured";
    }
  }

  grouping OVERLAY-OCNI-BGP-DYNAMIC-NEIGHBOR-PREFIX {
    description
      "An individual prefix from which dynamic neighbor
      connections are allowed";

    container state {
      description
        "Operational state parameters relating to the
        source prefix for the dynamic BGP neighbor
        connections";
      uses DYNAMIC-NEIGHBOR-PREFIX-STATE;
    }
  }

  grouping IBGP-STATE {
    description "IBGP STATE";
    leaf maximum-paths {
      type uint32;
      description
        "Maximum number of parallel paths to consider
        when using iBGP multipath";
    }
  }

  grouping IBGP {
    description "IBGP";

    container state {
      description "State information relating to iBGP multipath";
      uses IBGP-STATE;
    }
  }

  grouping EBGP-STATE {
    description "EBGP STATE";
    leaf allow-multiple-as {
      type boolean;
      description
        "Allow multipath to use paths from different
        neighbouring ASes";
    }
    leaf maximum-paths {
      type uint32;
      description
        "Maximum number of parallel paths to consider
        when using BGP multipath";
    }
  }

  grouping EBGP {
    description "EBGP";

    container state {
      description "State information relating to eBGP multipath";
      uses EBGP-STATE;
    }
  }

  grouping USE-MULTIPLE-PATHS-STATE {
    description "USE MULTIPLE PATHS STATE";
    leaf enabled {
      type boolean;
      description
        "Whether the use of multiple paths for the same
        NLRI is enabled for the neighbor";
    }
  }

  grouping OVERLAY-OCNI-BGP-USE-MULTIPLE-PATHS {
    description
      "Parameters related to the use of multiple paths
      for the same NLRI";

    container state {
      description "State parameters relating to multipath";
      uses USE-MULTIPLE-PATHS-STATE;
    }

    container ebgp {
      description "Multipath parameters for eBGP";
      uses EBGP;
    }

    container ibgp {
      description "Multipath parameters for iBGP";
      uses IBGP;
    }
  }

  grouping STATE {
    description "STATE";
    leaf external-route-distance {
      type uint8;
      description
        "Administrative distance for routes learned from
        external BGP (eBGP)";
    }
    leaf internal-route-distance {
      type uint8;
      description
        "Administrative distance for routes learned from
        internal BGP (iBGP)";
    }
  }

  grouping OVERLAY-OCNI-BGP-DEFAULT-ROUTE-DISTANCE {
    description
      "Administrative distance (or preference) assigned
      to routes received from different sources
      (external, internal, and local)";

    container state {
      description
        "State information relating to the default route
        distance";
      uses STATE;
    }
  }

  grouping L2VPN-EVPN-PREFIX-LIMIT-STATE {
    description "L2VPN EVPN PREFIX LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping L2VPN-EVPN-PREFIX-LIMIT {
    description "L2VPN EVPN PREFIX LIMIT";

    container state {
      description
        "State information relating to the prefix-limit
        for the AFI-SAFI";
      uses L2VPN-EVPN-PREFIX-LIMIT-STATE;
    }
  }

  grouping L2VPN-EVPN {
    description "L2VPN EVPN";

    container prefix-limit {
      description
        "Configure the maximum number of prefixes that
        will be accepted from a peer";
      uses L2VPN-EVPN-PREFIX-LIMIT;
    }
  }

  grouping L2VPNVPLS-PREFIX-LIMIT-STATE {
    description "L2VPNVPLS PREFIX LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping L2VPNVPLS-PREFIX-LIMIT {
    description "L2VPNVPLS PREFIX LIMIT";

    container state {
      description
        "State information relating to the prefix-limit
        for the AFI-SAFI";
      uses L2VPNVPLS-PREFIX-LIMIT-STATE;
    }
  }

  grouping L2VPNVPLS {
    description "L2VPNVPLS";

    container prefix-limit {
      description
        "Configure the maximum number of prefixes that
        will be accepted from a peer";
      uses L2VPNVPLS-PREFIX-LIMIT;
    }
  }

  grouping L3VPN-IPV6-MULTICAST-PREFIX-LIMIT-STATE {
    description "L3VPN IPV6 MULTICAST PREFIX LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping L3VPN-IPV6-MULTICAST-PREFIX-LIMIT {
    description "L3VPN IPV6 MULTICAST PREFIX LIMIT";

    container state {
      description
        "State information relating to the prefix-limit
        for the AFI-SAFI";
      uses L3VPN-IPV6-MULTICAST-PREFIX-LIMIT-STATE;
    }
  }

  grouping L3VPN-IPV6-MULTICAST {
    description "L3VPN IPV6 MULTICAST";

    container prefix-limit {
      description
        "Configure the maximum number of prefixes that
        will be accepted from a peer";
      uses L3VPN-IPV6-MULTICAST-PREFIX-LIMIT;
    }
  }

  grouping L3VPN-IPV4-MULTICAST-PREFIX-LIMIT-STATE {
    description "L3VPN IPV4 MULTICAST PREFIX LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping L3VPN-IPV4-MULTICAST-PREFIX-LIMIT {
    description "L3VPN IPV4 MULTICAST PREFIX LIMIT";

    container state {
      description
        "State information relating to the prefix-limit
        for the AFI-SAFI";
      uses L3VPN-IPV4-MULTICAST-PREFIX-LIMIT-STATE;
    }
  }

  grouping L3VPN-IPV4-MULTICAST {
    description "L3VPN IPV4 MULTICAST";

    container prefix-limit {
      description
        "Configure the maximum number of prefixes that
        will be accepted from a peer";
      uses L3VPN-IPV4-MULTICAST-PREFIX-LIMIT;
    }
  }

  grouping L3VPN-IPV6-UNICAST-PREFIX-LIMIT-STATE {
    description "L3VPN IPV6 UNICAST PREFIX LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping L3VPN-IPV6-UNICAST-PREFIX-LIMIT {
    description "L3VPN IPV6 UNICAST PREFIX LIMIT";

    container state {
      description
        "State information relating to the prefix-limit
        for the AFI-SAFI";
      uses L3VPN-IPV6-UNICAST-PREFIX-LIMIT-STATE;
    }
  }

  grouping L3VPN-IPV6-UNICAST {
    description "L3VPN IPV6 UNICAST";

    container prefix-limit {
      description
        "Configure the maximum number of prefixes that
        will be accepted from a peer";
      uses L3VPN-IPV6-UNICAST-PREFIX-LIMIT;
    }
  }

  grouping L3VPN-IPV4-UNICAST-PREFIX-LIMIT-STATE {
    description "L3VPN IPV4 UNICAST PREFIX LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping L3VPN-IPV4-UNICAST-PREFIX-LIMIT {
    description "L3VPN IPV4 UNICAST PREFIX LIMIT";

    container state {
      description
        "State information relating to the prefix-limit
        for the AFI-SAFI";
      uses L3VPN-IPV4-UNICAST-PREFIX-LIMIT-STATE;
    }
  }

  grouping L3VPN-IPV4-UNICAST {
    description "L3VPN IPV4 UNICAST";

    container prefix-limit {
      description
        "Configure the maximum number of prefixes that
        will be accepted from a peer";
      uses L3VPN-IPV4-UNICAST-PREFIX-LIMIT;
    }
  }

  grouping IPV6-LABELED-UNICAST-PREFIX-LIMIT-STATE {
    description "IPV6 LABELED UNICAST PREFIX LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping IPV6-LABELED-UNICAST-PREFIX-LIMIT {
    description "IPV6 LABELED UNICAST PREFIX LIMIT";

    container state {
      description
        "State information relating to the prefix-limit
        for the AFI-SAFI";
      uses IPV6-LABELED-UNICAST-PREFIX-LIMIT-STATE;
    }
  }

  grouping IPV6-LABELED-UNICAST {
    description "IPV6 LABELED UNICAST";

    container prefix-limit {
      description
        "Configure the maximum number of prefixes that
        will be accepted from a peer";
      uses IPV6-LABELED-UNICAST-PREFIX-LIMIT;
    }
  }

  grouping IPV4-LABELED-UNICAST-PREFIX-LIMIT-STATE {
    description "IPV4 LABELED UNICAST PREFIX LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping IPV4-LABELED-UNICAST-PREFIX-LIMIT {
    description "IPV4 LABELED UNICAST PREFIX LIMIT";

    container state {
      description
        "State information relating to the prefix-limit
        for the AFI-SAFI";
      uses IPV4-LABELED-UNICAST-PREFIX-LIMIT-STATE;
    }
  }

  grouping IPV4-LABELED-UNICAST {
    description "IPV4 LABELED UNICAST";

    container prefix-limit {
      description
        "Configure the maximum number of prefixes that
        will be accepted from a peer";
      uses IPV4-LABELED-UNICAST-PREFIX-LIMIT;
    }
  }

  grouping IPV6-UNICAST-STATE {
    description "IPV6 UNICAST STATE";
    leaf send-default-route {
      type boolean;
      description
        "If set to true, send the default-route to the
        neighbour(s)";
    }
  }

  grouping IPV6-UNICAST-PREFIX-LIMIT-STATE {
    description "IPV6 UNICAST PREFIX LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping IPV6-UNICAST-PREFIX-LIMIT {
    description "IPV6 UNICAST PREFIX LIMIT";

    container state {
      description
        "State information relating to the prefix-limit
        for the AFI-SAFI";
      uses IPV6-UNICAST-PREFIX-LIMIT-STATE;
    }
  }

  grouping IPV6-UNICAST {
    description "IPV6 UNICAST";

    container prefix-limit {
      description
        "Configure the maximum number of prefixes that
        will be accepted from a peer";
      uses IPV6-UNICAST-PREFIX-LIMIT;
    }

    container state {
      description
        "State information for common IPv4 and IPv6
        unicast parameters";
      uses IPV6-UNICAST-STATE;
    }
  }

  grouping IPV4-UNICAST-STATE {
    description "IPV4 UNICAST STATE";
    leaf send-default-route {
      type boolean;
      description
        "If set to true, send the default-route to the
        neighbour(s)";
    }
  }

  grouping PREFIX-LIMIT-STATE {
    description "PREFIX LIMIT STATE";
    leaf max-prefixes {
      type uint32;
      description
        "Maximum number of prefixes that will be accepted
        from the neighbour";
    }
    leaf prevent-teardown {
      type boolean;
      description
        "Do not tear down the BGP session when the
        maximum prefix limit is exceeded, but rather
        only log a warning";
    }
    leaf shutdown-threshold-pct {
      type uint8;
      description
        "Threshold on number of prefixes that can be
        received from a neighbour before generation of
        warning messages or log entries";
    }
    leaf restart-timer {
      type Yang2bag-string;
      units "second";
      description
        "Time interval in seconds after which the BGP
        session is re-established after being torn down
        due to exceeding the max-prefix limit";
    }
  }

  grouping PREFIX-LIMIT {
    description "PREFIX LIMIT";

    container state {
      description
        "State information relating to the prefix-limit
        for the AFI-SAFI";
      uses PREFIX-LIMIT-STATE;
    }
  }

  grouping IPV4-UNICAST {
    description "IPV4 UNICAST";

    container prefix-limit {
      description
        "Configure the maximum number of prefixes that
        will be accepted from a peer";
      uses PREFIX-LIMIT;
    }

    container state {
      description
        "State information for common IPv4 and IPv6
        unicast parameters";
      uses IPV4-UNICAST-STATE;
    }
  }

  grouping USE-MULTIPLE-PATHS-IBGP-STATE {
    description "USE MULTIPLE PATHS IBGP STATE";
    leaf maximum-paths {
      type uint32;
      description
        "Maximum number of parallel paths to consider
        when using iBGP multipath";
    }
  }

  grouping USE-MULTIPLE-PATHS-IBGP {
    description "USE MULTIPLE PATHS IBGP";

    container state {
      description "State information relating to iBGP multipath";
      uses USE-MULTIPLE-PATHS-IBGP-STATE;
    }
  }

  grouping USE-MULTIPLE-PATHS-EBGP-STATE {
    description "USE MULTIPLE PATHS EBGP STATE";
    leaf allow-multiple-as {
      type boolean;
      description
        "Allow multipath to use paths from different
        neighbouring ASes";
    }
    leaf maximum-paths {
      type uint32;
      description
        "Maximum number of parallel paths to consider
        when using BGP multipath";
    }
  }

  grouping USE-MULTIPLE-PATHS-EBGP {
    description "USE MULTIPLE PATHS EBGP";

    container state {
      description "State information relating to eBGP multipath";
      uses USE-MULTIPLE-PATHS-EBGP-STATE;
    }
  }

  grouping AFI-SAFI-USE-MULTIPLE-PATHS-STATE {
    description "AFI SAFI USE MULTIPLE PATHS STATE";
    leaf enabled {
      type boolean;
      description
        "Whether the use of multiple paths for the same
        NLRI is enabled for the neighbor";
    }
  }

  grouping USE-MULTIPLE-PATHS {
    description "USE MULTIPLE PATHS";

    container state {
      description "State parameters relating to multipath";
      uses AFI-SAFI-USE-MULTIPLE-PATHS-STATE;
    }

    container ebgp {
      description "Multipath parameters for eBGP";
      uses USE-MULTIPLE-PATHS-EBGP;
    }

    container ibgp {
      description "Multipath parameters for iBGP";
      uses USE-MULTIPLE-PATHS-IBGP;
    }
  }

  grouping AFI-SAFI-ROUTE-SELECTION-OPTIONS-STATE {
    description "AFI SAFI ROUTE SELECTION OPTIONS STATE";
    leaf always-compare-med {
      type boolean;
      description
        "Compare multi-exit discriminator (MED) value
        from different ASes when selecting the best
        route";
    }
    leaf ignore-as-path-length {
      type boolean;
      description
        "Ignore the AS path length when selecting the
        best path";
    }
    leaf external-compare-router-id {
      type boolean;
      description
        "When comparing similar routes received from
        external BGP peers, use the router-id as a
        criterion to select the active path";
    }
    leaf advertise-inactive-routes {
      type boolean;
      description "Advertise inactive routes to external peers";
    }
    leaf enable-aigp {
      type boolean;
      description
        "Flag to enable sending / receiving accumulated
        IGP attribute in routing updates";
    }
    leaf ignore-next-hop-igp-metric {
      type boolean;
      description
        "Ignore the IGP metric to the next-hop when
        calculating BGP best-path";
    }
  }

  grouping ROUTE-SELECTION-OPTIONS {
    description "ROUTE SELECTION OPTIONS";

    container state {
      description
        "State information for the route selection
        options";
      uses AFI-SAFI-ROUTE-SELECTION-OPTIONS-STATE;
    }
  }

  grouping AFI-SAFI-GRACEFUL-RESTART-STATE {
    description "AFI SAFI GRACEFUL RESTART STATE";
    leaf enabled {
      type boolean;
      description
        "This leaf indicates whether graceful-restart is
        enabled for this AFI-SAFI";
    }
  }

  grouping GRACEFUL-RESTART {
    description "GRACEFUL RESTART";

    container state {
      description "State information for BGP graceful-restart";
      uses AFI-SAFI-GRACEFUL-RESTART-STATE;
    }
  }

  grouping AFI-SAFI-STATE {
    description "AFI SAFI STATE";
    leaf afi-safi-name {
      type Yang2bag-string;
      description "AFI,SAFI";
    }
    leaf enabled {
      type boolean;
      description
        "This leaf indicates whether the IPv4 Unicast AFI
        ,SAFI is enabled for the neighbour or group";
    }
    leaf total-paths {
      type uint32;
      description "Total number of BGP paths within the context";
    }
    leaf total-prefixes {
      type uint32;
      description
        "Total number of BGP prefixes received within the
        context";
    }
  }

  grouping OVERLAY-OCNI-BGP-AFI-SAFI {
    description
      "AFI,SAFI configuration available for the
      neighbour or group";

    container state {
      description "State information relating to the AFI-SAFI";
      uses AFI-SAFI-STATE;
    }

    container graceful-restart {
      description "Parameters relating to BGP graceful-restart";
      uses GRACEFUL-RESTART;
    }

    container route-selection-options {
      description
        "Parameters relating to options for route
        selection";
      uses ROUTE-SELECTION-OPTIONS;
    }

    container use-multiple-paths {
      description
        "Parameters related to the use of multiple paths
        for the same NLRI";
      uses USE-MULTIPLE-PATHS;
    }

    container ipv4-unicast {
      description "IPv4 unicast configuration options";
      uses IPV4-UNICAST;
    }

    container ipv6-unicast {
      description "IPv6 unicast configuration options";
      uses IPV6-UNICAST;
    }

    container ipv4-labeled-unicast {
      description "IPv4 Labeled Unicast configuration options";
      uses IPV4-LABELED-UNICAST;
    }

    container ipv6-labeled-unicast {
      description "IPv6 Labeled Unicast configuration options";
      uses IPV6-LABELED-UNICAST;
    }

    container l3vpn-ipv4-unicast {
      description "Unicast IPv4 L3VPN configuration options";
      uses L3VPN-IPV4-UNICAST;
    }

    container l3vpn-ipv6-unicast {
      description "Unicast IPv6 L3VPN configuration options";
      uses L3VPN-IPV6-UNICAST;
    }

    container l3vpn-ipv4-multicast {
      description "Multicast IPv4 L3VPN configuration options";
      uses L3VPN-IPV4-MULTICAST;
    }

    container l3vpn-ipv6-multicast {
      description "Multicast IPv6 L3VPN configuration options";
      uses L3VPN-IPV6-MULTICAST;
    }

    container l2vpnvpls {
      description "BGP-signalled VPLS configuration options";
      uses L2VPNVPLS;
    }

    container l2vpn-evpn {
      description "BGP EVPN configuration options";
      uses L2VPN-EVPN;
    }
  }

  grouping CONFEDERATION-STATE {
    description "CONFEDERATION STATE";
    leaf enabled {
      type boolean;
      description
        "When this leaf is set to true it indicates that
        the local-AS is part of a BGP confederation";
    }
    leaf identifier {
      type uint32;
      description
        "Confederation identifier for the autonomous
        system";
    }
    leaf-list member-a {
      type uint32;
      description
        "Remote autonomous systems that are to be treated
        as part of the local confederation";
    }
  }

  grouping OVERLAY-OCNI-BGP-CONFEDERATION {
    description
      "Parameters indicating whether the local system
      acts as part of a BGP confederation";

    container state {
      description
        "State information relating to the BGP
        confederations";
      uses CONFEDERATION-STATE;
    }
  }

  grouping GRACEFUL-RESTART-STATE {
    description "GRACEFUL RESTART STATE";
    leaf enabled {
      type boolean;
      description
        "Enable or disable the graceful-restart
        capability";
    }
    leaf restart-time {
      type uint16;
      units "second";
      description
        "Estimated time (in seconds) for the local BGP
        speaker to restart a session";
    }
    leaf stale-routes-time {
      type Yang2bag-string;
      description
        "An upper-bound on the time thate stale routes
        will be retained by a router after a session is
        restarted";
    }
    leaf helper-only {
      type boolean;
      description "Enable graceful-restart in helper mode only";
    }
  }

  grouping OVERLAY-OCNI-BGP-GRACEFUL-RESTART {
    description
      "Parameters relating the graceful restart
      mechanism for BGP";

    container state {
      description
        "State information associated with
        graceful-restart";
      uses GRACEFUL-RESTART-STATE;
    }
  }

  grouping OVERLAY-OCNI-BGP-GLOBAL-STATE {
    description
      "State information relating to the global BGP
      router";
    leaf as {
      type uint32;
      description "Local autonomous system number of the router";
    }
    leaf router-id {
      type Yang2bag-string;
      description
        "Router id of the router - an unsigned 32-bit
        integer expressed in dotted quad notation";
    }
    leaf total-paths {
      type uint32;
      description "Total number of BGP paths within the context";
    }
    leaf total-prefixes {
      type uint32;
      description
        "Total number of BGP prefixes received within the
        context";
    }
  }

  grouping OVERLAY-OCNI-BGP-PROTOCOL-STATE {
    description
      "State parameters relating to the routing protocol
      instance";
    leaf identifier {
      type Yang2bag-string;
      description "The protocol identifier for the instance";
    }
    leaf name {
      type Yang2bag-string;
      description "A unique name for the protocol instance";
    }
    leaf enabled {
      type boolean;
      description
        "A boolean value indicating whether the local
        protocol instance is enabled";
    }
    leaf default-metric {
      type uint32;
      description
        "The default metric within the RIB for entries
        that are installed by this protocol instance";
    }
  }

  grouping OVERLAY-OCNI-BGP-STATE {
    description
      "Operational state parameters relating to a
      network instance";
    leaf route-distinguisher {
      type Yang2bag-string;
      description
        "The route distinguisher that should be used for
        the local VRF or VSI instance when it is
        signalled via BGP";
    }
    leaf-list enabled-address-family {
      type Yang2bag-string;
      description
        "The address families that are to be enabled for
        this network instance";
    }
  }
}
