module Cisco-IOS-XR-infra-xtc-agent-oper {

  /*** NAMESPACE / PREFIX DEFINITION ***/

  namespace "http://cisco.com/ns/yang"+
    "/Cisco-IOS-XR-infra-xtc-agent-oper";


  prefix "infra-xtc-agent-oper";

  /*** LINKAGE (IMPORTS / INCLUDES) ***/

  import ietf-inet-types { prefix "inet"; }

  import Cisco-IOS-XR-types { prefix "xr"; }

  include Cisco-IOS-XR-infra-xtc-agent-oper-sub2 {
    revision-date 2017-09-11;
  }

  include Cisco-IOS-XR-infra-xtc-agent-oper-sub1 {
    revision-date 2017-09-11;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-xtc-agent package operational data.

     This module contains definitions
     for the following management objects:
       pcc: Path-computation client in XTC
       xtc: xtc

     Copyright (c) 2013-2018 by Cisco Systems, Inc.
     All rights reserved.";

  revision "2017-09-11" {
    description
      "Initial version";
  }

  revision "2015-11-09" {
    description
      "IOS XR 6.0 revision.";
  }

  typedef Xtc-address-family {
    type enumeration {
      enum ipv4 {
        value 1;
        description "IPv4 address family";
      }
      enum ipv6 {
        value 2;
        description "IPv6 address family";
      }
    }
    description "Xtc address family";
  }

  container pcc {
    config false;
    description "Path-computation client in XTC";

    container plsps {
      description "PCC PLSP database in XTC";

      list plsp {
        key "plsp-id";
        description "PCC PLSP information";
        leaf plsp-id {
          type uint32;
          description "PLSP ID";
        }
        uses PCEP-PLSP-BAG;
      }
    }

    container peers {
      description "PCC peer database in XTC";

      list peer {
        key "peer-addr";
        description "PCC peer information";
        leaf peer-addr {
          type inet:ip-address-no-zone;
          description "Peer Address";
        }
        uses PCEP-CONN-BAG;
      }
    }
  }

  container xtc {
    config false;
    description "xtc";

    container policies {
      description "Policy database in XTC Agent";

      list policy {
        key "id";
        description "Policy information";
        leaf id {
          type uint32;
          description "Policy ID";
        }
        uses XTC-POLICY-BAG;
      }
    }

    container policy-summary {
      description "Summary of all policies";
      uses XTC-POLICY-SUMMARY-BAG;
    }

    container on-demand-colors {
      description "On-Demand Color database in XTC Agent";

      list on-demand-color {
        key "color";
        description "On Demand Color information";
        leaf color {
          type uint32;
          description "Color";
        }
        uses XTC-ON-DEMAND-COLOR-BAG;
      }
    }

    container forwarding {
      description "Forwarding information";

      container policy-forwardings {
        description "Forwarding information for policies";

        list policy-forwarding {
          key "name";
          description "Forwarding information for the policy";
          leaf name {
            type xr:Cisco-ios-xr-string;
            description "Policy Name";
          }
          uses XTC-FWDING-POLICY-BAG;
        }
      }
    }

    container controller {
      description "Controller information";

      container policy-requests {
        description "Table containing policy requests";

        list policy-request {
          key "source-address end-point-type end-point-address"+
            " color route-distinguisher";
          description "Policy request information";
          leaf source-address {
            type inet:ip-address-no-zone;
            description "Source Address";
          }
          leaf end-point-type {
            type Xtc-address-family;
            description "Endpoint Address Type";
          }
          leaf end-point-address {
            type inet:ip-address-no-zone;
            description "Endpoint Address";
          }
          leaf color {
            type uint32 {
              range "1..4294967295";
            }
            description "Color";
          }
          leaf route-distinguisher {
            type uint32 {
              range "0..4294967295";
            }
            description "Route Distinguisher";
          }
          uses XTC-CONTROLLER-POLICY-REQ-BAG;
        }
      }
    }

    container topology-summary {
      description "Node summary database";
      uses XTC-TOPO-SUMMARY-BAG;
    }

    container topology-nodes {
      description "Node database in XTC Agent";

      list topology-node {
        key "node-identifier";
        description "Node information";
        leaf node-identifier {
          type uint32;
          description "Node Identifier";
        }
        uses XTC-TOPO-NODE-BAG;
      }
    }

    container prefix-infos {
      description "Prefixes database in XTC Agent";

      list prefix-info {
        key "node-identifier";
        description "Prefix information";
        leaf node-identifier {
          type uint32;
          description "Node ID";
        }
        uses XTC-PFX-BAG;
      }
    }
  }
}
