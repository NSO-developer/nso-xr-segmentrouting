submodule Cisco-IOS-XR-lib-keychain-oper-sub1 {

  belongs-to Cisco-IOS-XR-lib-keychain-oper {
    prefix Cisco-IOS-XR-lib-keychain-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR lib-keychain package operational data.

     Copyright (c) 2013-2018 by Cisco Systems, Inc.
     All rights reserved.";

  revision "2018-01-31" {
    description
      "Fixed incorrect plural rendering.";
  }

  revision "2015-01-07" {
    description
      "IOS XR 5.3.1 revision.";
  }

  typedef Cryto-algo {
    type enumeration {
      enum not-configured {
        description "Not configured";
      }
      enum aes-128-cmac-96 {
        description "CMAC AES 12 bytes";
      }
      enum hmac-sha1-12 {
        description "HMAC SHA1 12 bytes";
      }
      enum md5 {
        description "MD5 16 bytes";
      }
      enum sha1 {
        description "SHA1 20 bytes";
      }
      enum hmac-md5 {
        description "HMAC MD5 16 bytes";
      }
      enum hmac-sha1-20 {
        description "HMAC SHA1 20 bytes";
      }
      enum aes-128-cmac {
        description "CMAC AES 32 bytes";
      }
      enum aes-256-cmac {
        description "CMAC AES 64 bytes";
      }
      enum hmac-sha1-96 {
        description "HMAC SHA1 12 bytes";
      }
      enum hmac-sha-256 {
        description "HMAC SHA256 32 bytes";
      }
    }
    description "Cryptographic algorithm type";
  }
  typedef Enc {
    type enumeration {
      enum password-type7 {
        value 0;
        description "Type 7 password type";
      }
      enum password-type6 {
        value 2;
        description "Type 6 Encryption";
      }
    }
    description "Type of password encryption";
  }

  grouping LIFETIME {
    description "Life time values associated with a key";
    leaf start {
      type string;
      description
        "Key life start time in format : day-of-week
        month date-of-month HH:MM:SS year eg: Thu Feb 1
        18:32:14 2011";
    }
    leaf end {
      type string;
      description
        "Key life end time in format : day-of-week month
        date-of-month HH:MM:SS year eg: Thu Feb 1 18:32
        :14 2011";
    }
    leaf duration {
      type string;
      units "second";
      description
        "Duration of the key in seconds. value 0xffffffff
        reflects infinite, never expires, is configured ";
    }
    leaf is-always-valid {
      type boolean;
      description "Is TRUE if duration is 0xffffffff ";
    }
    leaf is-valid-now {
      type boolean;
      description
        "Is TRUE if current time is betweenstart and end
        lifetime , else FALSE";
    }
  }

  grouping MACSEC {
    description "If it's a macsec key";
    leaf is-macsec-key {
      type boolean;
      description "To check if it's a macsec key";
    }
  }

  grouping KEY-ID {
    description "Key ID information";

    list key-id {
      description "key id";

      container macsec {
        description "To check if it's a macsec key";
        uses MACSEC;
      }

      container send-lifetime {
        description "Lifetime of the key";
        uses LIFETIME;
      }

      container accept-lifetime {
        description "Accept Lifetime of the key";
        uses LIFETIME;
      }
      leaf key-string {
        type string;
        description "Key string";
      }
      leaf type {
        type Enc;
        description "Type of key encryption";
      }
      leaf key-id {
        type string;
        description "Key ID";
      }
      leaf cryptographic-algorithm {
        type Cryto-algo;
        description "Cryptographic algorithm";
      }
    }
  }

  grouping KEY-CHAIN {
    description "Key chain config information";

    container key {
      description "Key properties";
      uses KEY-ID;
    }
    leaf accept-tolerance {
      type string;
      description
        "Accept tolerance is infinite if value is
        0xffffffff";
    }
  }
}
