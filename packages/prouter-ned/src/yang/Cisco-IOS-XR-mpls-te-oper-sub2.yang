submodule Cisco-IOS-XR-mpls-te-oper-sub2 {

  belongs-to Cisco-IOS-XR-mpls-te-oper {
    prefix Cisco-IOS-XR-mpls-te-oper;
  }

  /*** LINKAGE (IMPORTS / INCLUDES) ***/

  import ietf-inet-types { prefix "inet"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR mpls-te package operational data.

     Copyright (c) 2013-2018 by Cisco Systems, Inc.
     All rights reserved.";

  revision "2017-09-07" {
    description
      "Fixed type translation error.";
  }

  revision "2017-05-01" {
    description
      "Fixing backward compatibility error in module.";
  }

  revision "2015-11-09" {
    description
      "IOS XR 6.0 revision.";
  }

  typedef Tp-mid-lsp-status {
    type enumeration {
      enum up {
        description "Deprecated";
      }
      enum down {
        description "Deprecated";
      }
    }
    description "Deprecated";
  }

  grouping MPLS-TP-MID-SUMMARY-INFO {
    description "Deprecated";
    leaf mid-points {
      type uint32;
      description "Deprecated";
    }
    leaf up-forward-ls-ps {
      type uint32;
      description "Deprecated";
    }
    leaf down-forward-ls-ps {
      type uint32;
      description "Deprecated";
    }
    leaf up-reverse-ls-ps {
      type uint32;
      description "Deprecated";
    }
    leaf down-reverse-ls-ps {
      type uint32;
      description "Deprecated";
    }
  }

  grouping MPLS-TP-MID-LSP-INFO {
    description "Deprecated";
    leaf out-label {
      type uint32;
      description "Deprecated";
    }
    leaf out-link {
      type uint32;
      description "Deprecated";
    }
    leaf oam-refresh-interval {
      type uint32;
      description "Deprecated";
    }
    leaf outgoing-interface {
      type string;
      description "Deprecated";
    }
    leaf next-hop-address {
      type inet:ipv4-address;
      description "Deprecated";
    }
    leaf in-label {
      type uint32;
      description "Deprecated";
    }
    leaf bandwidth {
      type uint32;
      description "Deprecated";
    }
  }

  grouping MPLS-TP-MID-INFO {
    description "Deprecated";
    leaf midpoint-name {
      type string;
      description "Deprecated";
    }
    leaf tunnel-name {
      type string;
      description "Deprecated";
    }
    leaf source-node-id {
      type inet:ipv4-address;
      description "Deprecated";
    }
    leaf source-global-id {
      type uint32;
      description "Deprecated";
    }
    leaf source-tunnel-id {
      type uint32;
      description "Deprecated";
    }
    leaf lsp-id {
      type uint32;
      description "Deprecated";
    }
    leaf destination-node-id {
      type inet:ipv4-address;
      description "Deprecated";
    }
    leaf destination-global-id {
      type uint32;
      description "Deprecated";
    }
    leaf destination-tunnel-id {
      type uint32;
      description "Deprecated";
    }
    leaf forward-lsp-state {
      type Tp-mid-lsp-status;
      description "Deprecated";
    }
    leaf reverse-lsp-state {
      type Tp-mid-lsp-status;
      description "Deprecated";
    }
  }

  grouping MPLS-TP-DETAIL-MID-INFO {
    description "Deprecated";

    container brief-lsp-information {
      description "Deprecated";
      uses MPLS-TP-MID-INFO;
    }

    container forward-lsp {
      description "Deprecated";
      uses MPLS-TP-MID-LSP-INFO;
    }

    container reverse-lsp {
      description "Deprecated";
      uses MPLS-TP-MID-LSP-INFO;
    }
    leaf forward-lsp-reserved-bandwidth {
      type uint32;
      description "Deprecated";
    }
    leaf reverse-lsp-reserved-bandwidth {
      type uint32;
      description "Deprecated";
    }
  }
}
