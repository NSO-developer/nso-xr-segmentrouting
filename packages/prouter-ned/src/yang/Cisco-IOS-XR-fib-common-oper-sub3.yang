submodule Cisco-IOS-XR-fib-common-oper-sub3 {

  belongs-to Cisco-IOS-XR-fib-common-oper {
    prefix Cisco-IOS-XR-fib-common-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR fib-common package operational data.

     Copyright (c) 2013-2018 by Cisco Systems, Inc.
     All rights reserved.";

  revision "2017-09-07" {
    description
      "Fixed type translation error.";
  }

  revision "2017-05-01" {
    description
      "Fixing backward compatibility error in module.";
  }

  revision "2017-01-20" {
    description
      "IOS XR 6.2.1 revision";
  }

  revision "2015-11-09" {
    description
      "IOS XR 6.0 revision.";
  }

  typedef Bag-string {
    type string;
    description "Bag string";
  }

  grouping FIB-OC-INTERF-REF-STATE {
    description "FIB OC INTERF REF STATE";
    leaf interface {
      type string;
      description "Interface name";
    }
    leaf subinterface {
      type uint32;
      description "Sub-Interface index";
    }
  }

  grouping FIB-OC-INTERF-REF {
    description "FIB OC INTERF REF";

    container state {
      description "AFT entry interface ref state";
      uses FIB-OC-INTERF-REF-STATE;
    }
  }

  grouping FIB-OC-AFT-PATH-STATE {
    description "FIB OC AFT PATH STATE";
    leaf index {
      type uint64;
      description "Index";
    }
    leaf weight {
      type uint32;
      description "Weight";
    }
    leaf ip-address {
      type string;
      description "IP address";
    }
    leaf network-instance {
      type Bag-string;
      description "VRF name where the nexthop is resolved";
    }
    leaf-list popped-mpls-label-stack {
      type Bag-string;
      description "Popped mpls label stack";
    }
    leaf-list pushed-mpls-label-stack {
      type Bag-string;
      description "Pushed mpls label stack";
    }
  }

  grouping FIB-OC-AFT-PATH {
    description "FIB OC AFT PATH";

    container state {
      description "OC AFT entry next-hop state";
      uses FIB-OC-AFT-PATH-STATE;
    }

    container interface-ref {
      description "AFT entry next-hop interface ref";
      uses FIB-OC-INTERF-REF;
    }
  }

  grouping FIB-OC-PREFIX-STATE {
    description "FIB OC PREFIX STATE";
    leaf prefix-index {
      type string;
      description "IP prefix";
    }
    leaf label-index {
      type string;
      description "MPLS label";
    }
  }

  grouping FIB-OC-AFT-PREFIX {
    description "OC AFT entry";

    container state {
      description "State";
      uses FIB-OC-PREFIX-STATE;
    }

    list next-hop {
      description "Next hops";
      uses FIB-OC-AFT-PATH;
    }
  }
}
