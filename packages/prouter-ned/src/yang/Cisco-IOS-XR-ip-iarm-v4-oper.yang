module Cisco-IOS-XR-ip-iarm-v4-oper {

  /*** NAMESPACE / PREFIX DEFINITION ***/

  namespace "http://cisco.com/ns/yang/Cisco-IOS-XR-ip-iarm-v4-oper";


  prefix "ip-iarm-v4-oper";

  /*** LINKAGE (IMPORTS / INCLUDES) ***/

  import ietf-inet-types { prefix "inet"; }

  import Cisco-IOS-XR-types { prefix "xr"; }

  include Cisco-IOS-XR-ip-iarm-v4-oper-sub1 {
    revision-date 2017-05-01;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-iarm-v4 package operational data.

     This module contains definitions
     for the following management objects:
       ipv4arm: IPv4 Address Repository Manager (IPv4 ARM)
         operational data

     Copyright (c) 2013-2018 by Cisco Systems, Inc.
     All rights reserved.";

  revision "2017-05-01" {
    description
      "Fixing backward compatibility error in module.";
  }

  revision "2016-12-19" {
    description
      "IOS XR 6.2.1 revision.";
  }

  revision "2015-11-09" {
    description
      "IOS XR 6.0 revision.";
  }

  typedef Ipv4arm-prefix-length {
    type uint32 {
      range "0..32";
    }
    description "Ipv4arm prefix length";
  }

  container ipv4arm {
    config false;
    description
      "IPv4 Address Repository Manager (IPv4 ARM)
      operational data";

    container addresses {
      description "IPv4 ARM address database information";

      container vrfs {
        description "IPv4 ARM address database information per VRF";

        list vrf {
          key "vrf-name";
          description
            "IPv4 ARM address database information in a VRF";

          container networks {
            description
              "IPv4 ARM address database information by
              network";

            list network {
              description "An IPv4 Address in IPv4 ARM";
              leaf address {
                type inet:ipv4-address-no-zone;
                description "Address";
              }
              leaf prefix-length {
                type Ipv4arm-prefix-length;
                description "Prefix Length";
              }
              leaf handle {
                type xr:Interface-name;
                description "Interface";
              }
              uses IP-ARM-EDM-DB-NET-BAG-TYPE;
            }
          }

          container interfaces {
            description
              "IPv4 ARM address database information by
              interface";

            list interface {
              key "interface";
              description "An IPv4 address in IPv4 ARM";
              leaf interface {
                type xr:Interface-name;
                description "Interface";
              }
              uses IP-ARM-EDM-DB-IF-BAG-TYPE;
            }
          }
          leaf vrf-name {
            type string;
            description "VRF name";
          }
        }
      }
    }

    container summary {
      description "IPv4 ARM summary information";
      uses IP-ARM-EDM-SUMMARY-BAG-TYPE;
    }

    container vrf-summaries {
      description "IPv4 ARM VRFs summary information";

      list vrf-summary {
        key "vrf-name";
        description "IPv4 ARM VRF summary information";
        leaf vrf-name {
          type string;
          description "VRF name";
        }
        uses IP-ARM-EDM-DB-VRF-BAG-TYPE;
      }
    }

    container router-id {
      description "IPv4 ARM Router ID information";
      uses IP-ARM-EDM-DB-RTRID-BAG-TYPE;
    }
    leaf multicast-host-interface {
      type xr:Interface-name;
      description "Default multicast host interface";
    }
  }
}
