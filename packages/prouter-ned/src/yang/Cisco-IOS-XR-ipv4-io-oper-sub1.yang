submodule Cisco-IOS-XR-ipv4-io-oper-sub1 {

  belongs-to Cisco-IOS-XR-ipv4-io-oper {
    prefix Cisco-IOS-XR-ipv4-io-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv4-io package operational data.

     Copyright (c) 2013-2018 by Cisco Systems, Inc.
     All rights reserved.";

  revision "2015-10-20" {
    description
      "this schema file has all the latest changes.";
  }

  revision "2015-01-07" {
    description
      "IOS XR 5.3.1 revision.";
  }


  grouping IPV4-IO-ICMP-TRAFFIC {
    description "ICMP Traffic Information";
    leaf received {
      type uint32;
      description "ICMP Received";
    }
    leaf checksum-error {
      type uint32;
      description "ICMP Checksum Errors";
    }
    leaf unknown {
      type uint32;
      description "ICMP Unknown";
    }
    leaf output {
      type uint32;
      description "ICMP Transmitted";
    }
    leaf admin-unreachable-sent {
      type uint32;
      description "ICMP Admin Unreachable Sent";
    }
    leaf network-unreachable-sent {
      type uint32;
      description "ICMP Network Unreachable Sent";
    }
    leaf host-unreachable-sent {
      type uint32;
      description "ICMP Host Unreachable Sent";
    }
    leaf protocol-unreachable-sent {
      type uint32;
      description "ICMP Protocol Unreachable Sent";
    }
    leaf port-unreachable-sent {
      type uint32;
      description "ICMP Port Unreachable Sent";
    }
    leaf fragment-unreachable-sent {
      type uint32;
      description "ICMP Fragment Unreachable Sent";
    }
    leaf admin-unreachable-received {
      type uint32;
      description "ICMP Admin Unreachable Received";
    }
    leaf network-unreachable-received {
      type uint32;
      description "ICMP Network Unreachable Received";
    }
    leaf host-unreachable-received {
      type uint32;
      description "ICMP Host Unreachable Received";
    }
    leaf protocol-unreachable-received {
      type uint32;
      description "ICMP Protocol Unreachable Received";
    }
    leaf port-unreachable-received {
      type uint32;
      description "ICMP Port Unreachable Received";
    }
    leaf fragment-unreachable-received {
      type uint32;
      description "ICMP Fragment Unreachable Received";
    }
    leaf hopcount-sent {
      type uint32;
      description "ICMP Hopcount Sent";
    }
    leaf reassembly-sent {
      type uint32;
      description "ICMP Reassembly Sent";
    }
    leaf hopcount-received {
      type uint32;
      description "ICMP Hopcount Received";
    }
    leaf reassebly-received {
      type uint32;
      description "ICMP Reassembly Received";
    }
    leaf param-error-received {
      type uint32;
      description "ICMP Parameter Error Received";
    }
    leaf param-error-send {
      type uint32;
      description "ICMP Parameter Error Sent";
    }
    leaf echo-request-sent {
      type uint32;
      description "ICMP Echo Request Sent";
    }
    leaf echo-request-received {
      type uint32;
      description "ICMP Echo Request Sent";
    }
    leaf echo-reply-sent {
      type uint32;
      description "ICMP Echo Reply Sent";
    }
    leaf echo-reply-received {
      type uint32;
      description "ICMP Echo Reply Received";
    }
    leaf mask-request-sent {
      type uint32;
      description "ICMP Mask Sent";
    }
    leaf mask-request-received {
      type uint32;
      description "ICMP Mask Received";
    }
    leaf mask-reply-sent {
      type uint32;
      description "ICMP Mask Sent";
    }
    leaf mask-reply-received {
      type uint32;
      description "ICMP Mask Received";
    }
    leaf source-quench-received {
      type uint32;
      description "ICMP Source Quench";
    }
    leaf redirect-received {
      type uint32;
      description "ICMP Redirect Received";
    }
    leaf redirect-send {
      type uint32;
      description "ICMP Redirect Sent";
    }
    leaf timestamp-received {
      type uint32;
      description "ICMP Timestamp Received";
    }
    leaf timestamp-reply-received {
      type uint32;
      description "ICMP Timestamp Reply Received";
    }
    leaf router-advert-received {
      type uint32;
      description "ICMP Router Advertisement Received";
    }
    leaf router-solicit-received {
      type uint32;
      description "ICMP Router Solicited Received";
    }
  }

  grouping IPV4-IO-TRAFFIC {
    description "IP Traffic Information";
    leaf input-packets {
      type uint32;
      description "Input Packets";
    }
    leaf received-packets {
      type uint32;
      description "Received Packets";
    }
    leaf format-errors {
      type uint32;
      description "Format Errors";
    }
    leaf bad-hop-count {
      type uint32;
      description "Bad Hop Count";
    }
    leaf bad-source-address {
      type uint32;
      description "Bad Source Address";
    }
    leaf bad-header {
      type uint32;
      description "Bad Header";
    }
    leaf no-protocol {
      type uint32;
      description "No Protocol";
    }
    leaf no-gateway {
      type uint32;
      description "No Gateway";
    }
    leaf reassemble-input {
      type uint32;
      description "RaInput";
    }
    leaf reassembled {
      type uint32;
      description "Reassembled";
    }
    leaf reassemble-timeout {
      type uint32;
      description "Reassembly Timeout";
    }
    leaf reassemble-max-drop {
      type uint32;
      description "Reassembly Max Drop";
    }
    leaf reassemble-failed {
      type uint32;
      description "Reassembly Failed";
    }
    leaf options-present {
      type uint32;
      description "IP Options Present";
    }
    leaf bad-option {
      type uint32;
      description "Bad Option";
    }
    leaf unknown-option {
      type uint32;
      description "Unknown Option";
    }
    leaf bad-security-option {
      type uint32;
      description "Bad Security Option";
    }
    leaf basic-security-option {
      type uint32;
      description "Basic Security Option";
    }
    leaf extended-security-option {
      type uint32;
      description "Extended Security Option";
    }
    leaf cipso-option {
      type uint32;
      description "Cipso Option";
    }
    leaf strict-source-route-option {
      type uint32;
      description "Strict Source Route Option";
    }
    leaf loose-source-route-option {
      type uint32;
      description "Loose Source Route Option";
    }
    leaf record-route-option {
      type uint32;
      description "Record Route Option";
    }
    leaf sid-option {
      type uint32;
      description "SID Option";
    }
    leaf timestamp-option {
      type uint32;
      description "Timestamp Option";
    }
    leaf router-alert-option {
      type uint32;
      description "Router Alert Option";
    }
    leaf noop-option {
      type uint32;
      description "Noop Option";
    }
    leaf end-option {
      type uint32;
      description "End Option";
    }
    leaf packets-output {
      type uint32;
      description "Packets Output";
    }
    leaf packets-forwarded {
      type uint32;
      description "Packets Forwarded";
    }
    leaf packets-fragmented {
      type uint32;
      description "Packets Fragmented";
    }
    leaf fragment-count {
      type uint32;
      description "Fragment Count";
    }
    leaf encapsulation-failed {
      type uint32;
      description "Encapsulation Failed";
    }
    leaf no-router {
      type uint32;
      description "No Router";
    }
    leaf packet-too-big {
      type uint32;
      description "Packet Too Big";
    }
    leaf multicast-in {
      type uint32;
      description "Multicast In";
    }
    leaf multicast-out {
      type uint32;
      description "Multicast Out";
    }
    leaf broadcast-in {
      type uint32;
      description "Broadcast In";
    }
    leaf broadcast-out {
      type uint32;
      description "Broadcast Out";
    }
    leaf lisp-v4-encap {
      type uint32;
      description "Lisp IPv4 encapped packets";
    }
    leaf lisp-v4-decap {
      type uint32;
      description "Lisp IPv4 decapped packets";
    }
    leaf lisp-v6-encap {
      type uint32;
      description "Lisp IPv6 encapped packets";
    }
    leaf lisp-v6-decap {
      type uint32;
      description "Lisp IPv6 decapped packets";
    }
    leaf lisp-encap-error {
      type uint32;
      description "Lisp encap errors";
    }
    leaf lisp-decap-error {
      type uint32;
      description "Lisp decap errors";
    }
  }

  grouping IP-TRAFFIC {
    description "IP and ICMP Traffic Information";

    container ipv4-stats {
      description "IPv4 Network Stats";
      uses IPV4-IO-TRAFFIC;
    }

    container icmp-stats {
      description "ICMP Stats";
      uses IPV4-IO-ICMP-TRAFFIC;
    }
  }
}
