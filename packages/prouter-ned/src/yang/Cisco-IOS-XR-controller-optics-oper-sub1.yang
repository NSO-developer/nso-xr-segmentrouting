submodule Cisco-IOS-XR-controller-optics-oper-sub1 {

  belongs-to Cisco-IOS-XR-controller-optics-oper {
    prefix Cisco-IOS-XR-controller-optics-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR controller-optics package operational data.

     Copyright (c) 2013-2018 by Cisco Systems, Inc.
     All rights reserved.";

  revision "2017-09-07" {
    description
      "Fixed type translation error.";
  }

  revision "2017-05-01" {
    description
      "Fixing backward compatibility error in module.";
  }

  revision "2015-11-09" {
    description
      "IOS XR 6.0 revision.";
  }

  typedef Optics-ains-state-et {
    type enumeration {
      enum none {
        value 0;
        description "None";
      }
      enum active-running {
        value 1;
        description "Running";
      }
      enum active-pending {
        value 2;
        description "Pending";
      }
    }
    description "Optics ains state et";
  }
  typedef Ethernet-pmd {
    type enumeration {
      enum optics-eth-not-set {
        value 0;
        description "Not set";
      }
      enum optics-eth-10gbase-lrm {
        value 1;
        description "10GBASE LRM";
      }
      enum optics-eth-10gbase-lr {
        value 2;
        description "10GBASE LR";
      }
      enum optics-eth-10gbase-zr {
        value 3;
        description "10GBASE ZR";
      }
      enum optics-eth-10gbase-er {
        value 4;
        description "10GBASE ER";
      }
      enum optics-eth-10gbase-sr {
        value 5;
        description "10GBASE SR";
      }
      enum optics-eth-10gbase {
        value 6;
        description "10GBASE T";
      }
      enum optics-eth-40gbase-cr4 {
        value 7;
        description "40GBASE CR4";
      }
      enum optics-eth-40gbase-sr4 {
        value 8;
        description "40GBASE SR4";
      }
      enum optics-eth-40gbase-lr4 {
        value 9;
        description "40GBASE LR4";
      }
      enum optics-eth-40gbase-er4 {
        value 10;
        description "40GBASE ER4";
      }
      enum optics-eth-40gbase-psm4 {
        value 11;
        description "40GBASE PSM4";
      }
      enum optics-eth-40gbase-csr4 {
        value 12;
        description "40GBASE CSR4";
      }
      enum optics-eth-40gbase-sr-bd {
        value 13;
        description "40GBASE SR BD";
      }
      enum optics-eth-40g-aoc {
        value 14;
        description "40G AOC";
      }
      enum optics-eth-4x10gbase-lr {
        value 15;
        description "4X10GBASE LR";
      }
      enum optics-eth-4x10gbase-sr {
        value 16;
        description "4X10GBASE SR";
      }
      enum optics-eth-100g-aoc {
        value 17;
        description "100G AOC";
      }
      enum optics-eth-100g-acc {
        value 18;
        description "100G ACC";
      }
      enum optics-eth-100gbase-sr10 {
        value 19;
        description "100GBASE SR10";
      }
      enum optics-eth-100gbase-sr4 {
        value 20;
        description "100GBASE SR4";
      }
      enum optics-eth-100gbase-lr4 {
        value 21;
        description "100GBASE LR4";
      }
      enum optics-eth-100gbase-er4 {
        value 22;
        description "100GBASE ER4";
      }
      enum optics-eth-100gbase-cwdm4 {
        value 23;
        description "100GBASE CWDM4";
      }
      enum optics-eth-100gbase-clr4 {
        value 24;
        description "100GBASE CLR4";
      }
      enum optics-eth-100gbase-psm4 {
        value 25;
        description "100GBASE PSM4";
      }
      enum optics-eth-100gbase-cr4 {
        value 26;
        description "100GBASE CR4";
      }
      enum optics-eth-100gbase-al {
        value 27;
        description "100GBASE AL";
      }
      enum optics-eth-100gbase-pl {
        value 28;
        description "100GBASE PL";
      }
      enum optics-eth-undefined {
        value 29;
        description "Eth Undefined";
      }
    }
    description "Ethernet Pmd Type";
  }
  typedef Sonet-application-code {
    type enumeration {
      enum optics-sonet-not-set {
        value 0;
        description "Not Set";
      }
      enum optics-vsr2000-3r2 {
        value 1;
        description "VSR2000 3R2";
      }
      enum optics-vsr2000-3r3 {
        value 2;
        description "VSR2000 3R3";
      }
      enum optics-vsr2000-3r5 {
        value 3;
        description "VSR2000 3R5";
      }
      enum optics-sonet-undefined {
        value 4;
        description "Undefined";
      }
    }
    description "Sonet application code";
  }
  typedef Otn-application-code {
    type enumeration {
      enum optics-not-set {
        value 0;
        description "Not Set";
      }
      enum optics-p1l1-2d1 {
        value 1;
        description "P1L1 2D1";
      }
      enum optics-p1s1-2d2 {
        value 2;
        description "P1S1 2D2";
      }
      enum optics-p1l1-2d2 {
        value 3;
        description "P1L1 2D2";
      }
      enum optics-undefined {
        value 4;
        description "Undefined";
      }
    }
    description "Otn application code";
  }
  typedef Fiber-connector {
    type enumeration {
      enum optics-connect-or-not-set {
        value 0;
        description "Not Set";
      }
      enum optics-sc-connect-or {
        value 1;
        description "SC";
      }
      enum optics-lc-connect-or {
        value 2;
        description "LC";
      }
      enum optics-mpo-connect-or {
        value 3;
        description "MPO";
      }
      enum optics-undefined-connect-or {
        value 4;
        description "Undefined";
      }
    }
    description "Fiber connector";
  }
  typedef Optics-amplifier-safety-control-mode {
    type enumeration {
      enum optics-amplifier-safety-mode-invalid {
        value 0;
        description "Invalid";
      }
      enum optics-amplifier-safety-mode-auto {
        value 1;
        description "auto";
      }
      enum optics-amplifier-safety-mode-disabled {
        value 2;
        description "disabled";
      }
    }
    description "Optics amplifier safety control mode";
  }
  typedef Optics-amplifier-gain-range {
    type enumeration {
      enum optics-amplifier-gain-range-invalid {
        value 0;
        description "Invalid";
      }
      enum optics-amplifier-gain-range-normal {
        value 1;
        description "Normal";
      }
      enum optics-amplifier-gain-range-ext-end-ed {
        value 2;
        description "Extended";
      }
    }
    description "Optics amplifier gain range";
  }
  typedef Optics-amplifier-control-mode {
    type enumeration {
      enum automatic {
        value 1;
        description "Automatic";
      }
      enum manual {
        value 2;
        description "Manual";
      }
    }
    description "Optics amplifier control mode";
  }
  typedef Optics-port-status {
    type enumeration {
      enum active {
        value 0;
        description "Active";
      }
      enum standby {
        value 1;
        description "Standby";
      }
    }
    description "Optics port status";
  }
  typedef Optics-port {
    type enumeration {
      enum com {
        value 0;
        description "Com";
      }
      enum line {
        value 1;
        description "Line";
      }
      enum osc {
        value 2;
        description "Osc";
      }
      enum com-check {
        value 3;
        description "Com Check";
      }
      enum work {
        value 4;
        description "Working";
      }
      enum prot {
        value 5;
        description "Protected";
      }
    }
    description "Optics port";
  }
  typedef Optics-fec {
    type enumeration {
      enum fec-none {
        value 0;
        description "FEC NONE";
      }
      enum fec-hg15 {
        value 1;
        description "ENHANCED FEC H15";
      }
      enum fec-hg25 {
        value 2;
        description "ENHANCED FEC H25";
      }
      enum fec-hg15-de {
        value 4;
        description "FEC HG15 DE";
      }
      enum fec-hg25-de {
        value 8;
        description "FEC HG25 DE";
      }
      enum fec-enabled {
        value 16;
        description "FEC ENABLED";
      }
      enum fec-not-set {
        value 32;
        description "FEC DISABLED";
      }
      enum fec-cl91 {
        value 64;
        description "FEC CL91";
      }
    }
    description "Optics fec";
  }
  typedef Optics-phy {
    type enumeration {
      enum not-set {
        value 0;
        description "Not set";
      }
      enum invalid {
        value 1;
        description "Invalid";
      }
      enum long-reach-four-lanes {
        value 2;
        description "Long reach 4 lanes";
      }
      enum short-reach-ten-lanes {
        value 3;
        description "Short reach 10 lanes";
      }
      enum short-reach-one-lane {
        value 4;
        description "Short reach 1 lane";
      }
      enum long-reach-one-lane {
        value 5;
        description "Long reach 1 lane";
      }
      enum short-reach-four-lanes {
        value 6;
        description "Short reach 4 lanes";
      }
      enum copper-four-lanes {
        value 7;
        description "Copper 4 lanes";
      }
      enum active-optical-cable {
        value 8;
        description "Active optical cable";
      }
      enum fourty-gig-e-long-reach-four-lanes {
        value 9;
        description "Long reach 4 lanes";
      }
      enum fourty-gig-e-short-reach-four-lanes {
        value 10;
        description "Short reach 4 lanes";
      }
      enum cwdm-four-lanes {
        value 11;
        description "CWDM 4 lanes";
      }
      enum extended-reach-four-lanes {
        value 12;
        description "Extended reach 4 lanes";
      }
      enum psm-four-lanes {
        value 13;
        description "PSM 4 lanes";
      }
      enum active-copper-cable {
        value 14;
        description "Active copper cable";
      }
      enum fourty-gig-e-extended-reach-four-lanes {
        value 15;
        description "Extended reach 4 lanes";
      }
      enum four-x-ten-gig-e-short-reach-one-lane {
        value 16;
        description "Short reach 1 lane";
      }
      enum fourty-gig-epsm-four-lanes {
        value 17;
        description "PSM 4 lanes";
      }
      enum fourty-gig-e-copper-four-lanes {
        value 18;
        description "Copper 4 lanes";
      }
      enum long-reach-mm-one-lane {
        value 19;
        description "Long reach MM 1 lane";
      }
      enum copper-short-reach {
        value 20;
        description "Copper Short reach 4 lanes";
      }
      enum short-reach-srbd {
        value 21;
        description "Short reach BD 4 lanes";
      }
      enum copper-one-lane {
        value 22;
        description "Copper One Lane";
      }
      enum four-x-ten-gig-e-long-reach-one-lane {
        value 23;
        description "Long reach 1 lane";
      }
      enum fourty-gig-eaoc-four-lanes {
        value 24;
        description "Active optical cable";
      }
      enum extended-one-lane {
        value 25;
        description "Extended One Lane";
      }
      enum zr-one-lane {
        value 26;
        description "ZR One Lane";
      }
      enum dwdm-one-lane {
        value 27;
        description "DWDM One Lane";
      }
      enum sx-one-lane {
        value 28;
        description "SX One Lane";
      }
      enum lx-one-lane {
        value 29;
        description "LX One Lane";
      }
      enum ex-one-lane {
        value 30;
        description "EX One Lane";
      }
      enum zx-one-lane {
        value 31;
        description "ZX One Lane";
      }
      enum ba-set-one-lane {
        value 32;
        description "BASE_T One Lane";
      }
      enum aoc-one-lane {
        value 33;
        description "Active Optical 1 Lane";
      }
      enum active-copper-one-lane {
        value 34;
        description "Active Copper 1 Lane";
      }
      enum fourty-gig-eacu-four-lanes {
        value 35;
        description "Active Copper 4 Lanes";
      }
      enum four-x-ten-gig-eacu-one-lanes {
        value 36;
        description "Active Copper 1 Lane";
      }
      enum four-x-ten-gig-ecu-one-lanes {
        value 37;
        description "Copper 1 Lanes";
      }
      enum four-x-ten-gig-eaoc-one-lanes {
        value 38;
        description "Active Optics 1 Lane";
      }
      enum twenty-five-gig-short-reach-one-lane {
        value 39;
        description "Short reach 1 lane";
      }
      enum twenty-five-gig-long-reach-one-lane {
        value 40;
        description "Long reach 1 lane";
      }
      enum twenty-five-gig-extended-reach-one-lane {
        value 41;
        description "Extended reach 1 lane";
      }
      enum twenty-five-gig-copper-one-lane {
        value 42;
        description "Copper One Lane";
      }
      enum twenty-five-gig-active-optical-one-lane {
        value 43;
        description "Active Optical One Lane";
      }
      enum hundred-gig-edwdm-two {
        value 44;
        description "100GE DWDM Optics";
      }
      enum fourty-gig-plr4-four-lanes {
        value 45;
        description "PLR4 Optics";
      }
      enum fourty-gig-esr4-four-lanes {
        value 46;
        description "ESR4 Optics";
      }
      enum smsr-four-lanes {
        value 47;
        description "SMSR Optics";
      }
      enum cazadero-rqsa {
        value 48;
        description "Cazadero R";
      }
      enum trunk-port-cfp2 {
        value 49;
        description "CFP2 DWDM Optics";
      }
      enum short-reach1-lane {
        value 50;
        description "Short reach 1 lane";
      }
      enum inmd-reach1lane {
        value 51;
        description "Inmd reach 1 lane";
      }
      enum long-reach1-lane {
        value 52;
        description "Long reach 1 lane";
      }
      enum twenty-five-gig-ecu-one-lanes {
        value 53;
        description "Copper 1 Lanes";
      }
      enum hundred-gig-e {
        value 54;
        description "ExtentedReach4Lane";
      }
      enum ten-gig-bx {
        value 55;
        description "10G BX optics";
      }
      enum one-geige {
        value 56;
        description "1G BX optics";
      }
      enum ten-x-ten-gig-e-long-reach-one-lane {
        value 57;
        description "Long Reach 1 Lane";
      }
      enum ten-x-ten-gig-e-extended-reach-one-lane {
        value 58;
        description "Extended Reach 1 Lane";
      }
      enum passive-copper-one-lane {
        value 59;
        description "Passive Copper One Lane";
      }
      enum ten-gig-ecwdm {
        value 60;
        description "TenGigE CWDM One Lane";
      }
      enum one-gig-ecwdm {
        value 61;
        description "One GigE CWDM One Lane";
      }
      enum one-gig-edwdm {
        value 62;
        description "One GigE DWDM One Lane";
      }
      enum fx-one-lane {
        value 63;
        description "FX One Lane";
      }
      enum ten-gig-emrdwdm {
        value 64;
        description "TenGigE Multi Rate DWDM 1 Lane";
      }
      enum ten-gig-e-edge-performance {
        value 65;
        description "TenGigE Edge Performance 1 Lane";
      }
      enum one-gig-csfp {
        value 66;
        description "OneGig CSFP optics";
      }
    }
    description "Optics phy type";
  }
  typedef Optics-form-factor {
    type enumeration {
      enum not-set {
        value 0;
        description "Not set";
      }
      enum invalid {
        value 1;
        description "Invalid";
      }
      enum cpak {
        value 2;
        description "CPAK";
      }
      enum cxp {
        value 3;
        description "CXP";
      }
      enum sfp-plus {
        value 4;
        description "SFP+";
      }
      enum qsfp {
        value 5;
        description "QSFP";
      }
      enum qsfp-plus {
        value 6;
        description "QSFP+";
      }
      enum qsfp28 {
        value 7;
        description "QSFP28";
      }
      enum sfp {
        value 8;
        description "SFP";
      }
      enum cfp {
        value 9;
        description "CFP";
      }
      enum cfp2 {
        value 10;
        description "CFP2";
      }
      enum cfp2-aco {
        value 11;
        description "CFP2 ACO";
      }
      enum cfp2-dco {
        value 12;
        description "CFP2 DCO";
      }
      enum cfp4 {
        value 13;
        description "CFP4";
      }
      enum xfp {
        value 14;
        description "XFP";
      }
      enum x2 {
        value 15;
        description "X2";
      }
      enum non-pluggable {
        value 16;
        description "Non pluggable";
      }
      enum other {
        value 17;
        description "Other";
      }
    }
    description "Optics form factor";
  }
  typedef Optics-controller-state {
    type enumeration {
      enum optics-state-up {
        value 0;
        description "Up";
      }
      enum optics-state-down {
        value 1;
        description "Down";
      }
      enum optics-state-admin-down {
        value 2;
        description "Administratively Down";
      }
    }
    description "Optics controller state";
  }
  typedef Optics-led-state {
    type enumeration {
      enum off {
        value 0;
        description "Off";
      }
      enum green-on {
        value 1;
        description "Green";
      }
      enum green-flashing {
        value 2;
        description "Green Flashing";
      }
      enum yellow-on {
        value 3;
        description "Yellow";
      }
      enum yellow-flashing {
        value 4;
        description "Yellow Flashing";
      }
      enum red-on {
        value 5;
        description "Red";
      }
      enum red-flashing {
        value 6;
        description "Red Flashing";
      }
    }
    description "Optics led state";
  }
  typedef Optics-modulation {
    type enumeration {
      enum mod-bpsk {
        value 1;
        description "BPSK";
      }
      enum mod-qpsk {
        value 2;
        description "QPSK";
      }
      enum mod-8qam {
        value 3;
        description "8QAM";
      }
      enum mod-16qam {
        value 4;
        description "16QAM";
      }
      enum mod-32qam {
        value 5;
        description "32QAM";
      }
      enum mod-64qam {
        value 6;
        description "64QAM";
      }
      enum mod-bpsk-qpsk {
        value 7;
        description "BPSK QPSK";
      }
      enum mod-qpsk-8qam {
        value 8;
        description "QPSK 8QAM";
      }
      enum mod-8qam-16qam {
        value 9;
        description "8QAM 16QAM";
      }
      enum mode-16qam-32qam {
        value 10;
        description "16QAM 32QAM";
      }
      enum mod-32qam-64qam {
        value 11;
        description "32QAM 64QAM";
      }
    }
    description "Optics modulation";
  }
  typedef Optics-laser-state {
    type enumeration {
      enum on {
        value 0;
        description "On";
      }
      enum off {
        value 1;
        description "Off";
      }
      enum unknown {
        value 2;
        description "Unknown";
      }
      enum apr {
        value 3;
        description "Apr";
      }
      enum na {
        value 4;
        description "N/A";
      }
    }
    description "Optics laser state";
  }
  typedef Optics {
    type enumeration {
      enum optics-unknown {
        value 0;
        description "Unknow Optics Type";
      }
      enum optics-grey {
        value 1;
        description "Grey Optics";
      }
      enum optics-dwdm {
        value 2;
        description "DWDM Optics";
      }
      enum optics-cwdm {
        value 3;
        description "CWDM Optics";
      }
    }
    description "Optics";
  }
  typedef Optics-tas {
    type enumeration {
      enum tas-ui-oos {
        value 0;
        description "Out Of Service";
      }
      enum tas-ui-main {
        value 1;
        description "Maintenance";
      }
      enum tas-ui-is {
        value 2;
        description "In Service";
      }
      enum tas-ui-ains {
        value 3;
        description "Automatic In Service";
      }
    }
    description "Optics tas";
  }
  typedef Optics-wave-band {
    type enumeration {
      enum c-band {
        value 0;
        description "C BAND";
      }
      enum l-band {
        value 1;
        description "L BAND";
      }
      enum c-band-odd {
        value 2;
        description "C ODD";
      }
      enum c-band-even {
        value 3;
        description "C EVEN";
      }
      enum invalid-band {
        value 4;
        description "Invalid";
      }
    }
    description "Optics wave band";
  }

  grouping OPTICS-DB-INFO {
    description " Optics DB Info";

    container network-srlg-info {
      description "Network SRLG information";
      uses OPTICS-EDM-NETWORK-SRLG-INFO;
    }
    leaf transport-admin-state {
      type Optics-tas;
      description "Transport Admin State";
    }
    leaf controller-state {
      type Optics-controller-state;
      description
        "Optics controller state: Up, Down or
        Administratively Down";
    }
  }

  grouping OPTICS-AINS-HW-INFO {
    description "OPTICS AINS information";
    leaf ains-state {
      type Optics-ains-state-et;
      description "AINS State";
    }
    leaf ains-timer-minutes {
      type uint32;
      units "minute";
      description "AINS Timer in Minutes";
    }
    leaf ains-remaining-secs {
      type uint32;
      units "second";
      description "AINS Remaining Seconds";
    }
  }

  grouping EXT-PARAM-EDM-ALARM-INFO {
    description "Extended DOM Alarm Information";

    container lo-snr {
      description "Low SNR Alarm for Lane1";
      uses OPTICS-ALARM-DETAIL;
    }

    container hi-snr1 {
      description "High SNR Alarm for Lane1";
      uses OPTICS-ALARM-DETAIL;
    }

    container lo-snr1 {
      description "Low SNR Alarm for Lane2";
      uses OPTICS-ALARM-DETAIL;
    }

    container hi-snr2 {
      description "High SNR Alarm for Lane2";
      uses OPTICS-ALARM-DETAIL;
    }

    container lo-isi1 {
      description "Low ISI Correction Alarm for Lane1";
      uses OPTICS-ALARM-DETAIL;
    }

    container hi-isi1 {
      description "High ISI Correction Alarm for Lane1";
      uses OPTICS-ALARM-DETAIL;
    }

    container lo-isi2 {
      description "Low ISI Correction Alarm for Lane2";
      uses OPTICS-ALARM-DETAIL;
    }

    container hi-isi2 {
      description "High ISI Correction Alarm for Lane2";
      uses OPTICS-ALARM-DETAIL;
    }

    container lo-pam1 {
      description "Low PAM Rate Alarm for Lane1";
      uses OPTICS-ALARM-DETAIL;
    }

    container hi-pam1 {
      description "High PAM Rate Alarm for Lane1";
      uses OPTICS-ALARM-DETAIL;
    }

    container lo-pam2 {
      description "Low PAM Rate Alarm for Lane2";
      uses OPTICS-ALARM-DETAIL;
    }

    container hi-pam2 {
      description "High PAM Rate Alarm for Lane2";
      uses OPTICS-ALARM-DETAIL;
    }

    container lo-tec1 {
      description "Low TEC Current Alarm for Lane1";
      uses OPTICS-ALARM-DETAIL;
    }

    container hi-tec1 {
      description "High TEC Current Alarm for Lane1";
      uses OPTICS-ALARM-DETAIL;
    }

    container lo-tec2 {
      description "Low TEC Current Alarm for Lane2";
      uses OPTICS-ALARM-DETAIL;
    }

    container hi-tec2 {
      description "High TEC Current Alarm for Lane2";
      uses OPTICS-ALARM-DETAIL;
    }

    container lo-laser-freq1 {
      description
        "Low Laser Differential Frequency Alarm for Lane1";
      uses OPTICS-ALARM-DETAIL;
    }

    container hi-laser-freq1 {
      description
        "High Laser Differential Frequency Alarm for
        Lane1";
      uses OPTICS-ALARM-DETAIL;
    }

    container lo-laser-freq2 {
      description
        "Low Laser Differential Frequency Alarm for Lane2";
      uses OPTICS-ALARM-DETAIL;
    }

    container hi-laser-freq2 {
      description
        "High Laser Differential Frequency Alarm for
        Lane2";
      uses OPTICS-ALARM-DETAIL;
    }

    container hi-pre-fecber-cur-acc {
      description "High Pre FEC BER Current Accumulated Alarm";
      uses OPTICS-ALARM-DETAIL;
    }

    container hi-pre-fecber-min {
      description "High Pre FEC BER Min Alarm";
      uses OPTICS-ALARM-DETAIL;
    }

    container hi-pre-fecber-max {
      description "High Pre FEC BER Max Alarm";
      uses OPTICS-ALARM-DETAIL;
    }

    container hi-pre-fecber-prior-acc {
      description "High Pre FEC BER Prior Accumulated Alarm";
      uses OPTICS-ALARM-DETAIL;
    }

    container hi-pre-fecber-cur {
      description "High Pre FEC BER Current Alarm";
      uses OPTICS-ALARM-DETAIL;
    }

    container hi-uncorrected-ber-cur-acc {
      description "High Uncorrected BER Current Accumulated Alarm";
      uses OPTICS-ALARM-DETAIL;
    }

    container hi-uncorrected-ber-min {
      description "High Uncorrected BER Min Alarm";
      uses OPTICS-ALARM-DETAIL;
    }

    container hi-uncorrected-ber-max {
      description "High Uncorrected BER Max Alarm";
      uses OPTICS-ALARM-DETAIL;
    }

    container hi-uncorrected-ber-prior-acc {
      description "High Uncorrected BER Prior Accumulated Alarm";
      uses OPTICS-ALARM-DETAIL;
    }

    container hi-uncorrected-ber-cur {
      description "High Uncorrected BER Current Alarm";
      uses OPTICS-ALARM-DETAIL;
    }
  }

  grouping OPTICS-EXT-THRESHOLD-PARAM {
    description
      "extended monitored parameter threshold
      information";
    leaf snr-alarm-high-threshold {
      type int32;
      description "High threshold alarm for SNR";
    }
    leaf snr-alarm-low-threshold {
      type int32;
      description "Low threshold alarm for SNR";
    }
    leaf snr-warn-high-threshold {
      type int32;
      description "High threshold warning for SNR";
    }
    leaf snr-warn-low-threshold {
      type int32;
      description "Low threshold warning for SNR";
    }
    leaf isi-correction-alarm-high-threshold {
      type int32;
      description "High threshold alarm for ISI Correction";
    }
    leaf isi-correction-alarm-low-threshold {
      type int32;
      description "Low threshold alarm for ISI Correction";
    }
    leaf isi-correction-warn-high-threshold {
      type int32;
      description "High threshold warning for ISI Correction";
    }
    leaf isi-correction-warn-low-threshold {
      type int32;
      description "Low threshold warning for ISI Correction";
    }
    leaf pam-rate-alarm-high-threshold {
      type int32;
      description "High threshold alarm for PAM Rate";
    }
    leaf pam-rate-alarm-low-threshold {
      type int32;
      description "Low threshold alarm for PAM Rate";
    }
    leaf pam-rate-warn-high-threshold {
      type int32;
      description "High threshold warning for PAM Rate";
    }
    leaf pam-rate-warn-low-threshold {
      type int32;
      description "Low threshold warning for PAM Rate";
    }
    leaf pre-fec-ber-alarm-high-threshold {
      type int64;
      description "High threshold alarm for Pre FEC BER";
    }
    leaf pre-fec-ber-alarm-low-threshold {
      type int64;
      description "Low threshold alarm for Pre FEC BER";
    }
    leaf pre-fec-ber-warn-high-threshold {
      type int64;
      description "High threshold warning for Pre FEC BER";
    }
    leaf pre-fec-ber-warn-low-threshold {
      type int64;
      description "Low threshold warning for Pre FEC BER";
    }
    leaf uncorrected-ber-alarm-high-threshold {
      type int64;
      description "High threshold alarm for Uncorrected BER";
    }
    leaf uncorrected-ber-alarm-low-threshold {
      type int64;
      description "Low threshold alarm for Uncorrected BER";
    }
    leaf uncorrected-ber-warn-high-threshold {
      type int64;
      description "High threshold warning for Uncorrected BER";
    }
    leaf uncorrected-ber-warn-low-threshold {
      type int64;
      description "Low threshold warning for Uncorrected BER";
    }
    leaf tec-current-alarm-high-threshold {
      type int32;
      description "High threshold alarm for TEC Current";
    }
    leaf tec-current-alarm-low-threshold {
      type int32;
      description "Low threshold alarm for TEC Current";
    }
    leaf tec-current-warn-high-threshold {
      type int32;
      description "High threshold warning for TEC Current";
    }
    leaf tec-current-warn-low-threshold {
      type int32;
      description "Low threshold warning for TEC Current";
    }
    leaf laser-diff-frequency-alarm-high-threshold {
      type int32;
      description
        "High Threshold Alarm for Differential Laser
        Frequency";
    }
    leaf laser-diff-frequency-alarm-low-threshold {
      type int32;
      description
        "Low Threshold Alarm for Differential Laser
        Frequency";
    }
    leaf laser-diff-frequency-warn-high-threshold {
      type int32;
      description
        "High Threshold Warning for Differential Laser
        Frequency";
    }
    leaf laser-diff-frequency-warn-low-threshold {
      type int32;
      description
        "Low Threshold Warning for Differential Laser
        Frequency";
    }
    leaf laser-diff-temperature-alarm-high-threshold {
      type int32;
      description
        "High Threshold Alarm for Differential Laser
        Temperature";
    }
    leaf laser-diff-temperature-alarm-low-threshold {
      type int32;
      description
        "Low Threshold Alarm for Differential Laser
        Temperature";
    }
    leaf laser-diff-temperature-warn-high-threshold {
      type int32;
      description
        "High Threshold Warning for Differential Laser
        Temperature";
    }
    leaf laser-diff-temperature-warn-low-threshold {
      type int32;
      description
        "Low Threshold Warning for Differential Laser
        Temperature";
    }
    leaf pre-fec-ber-latched-min-alarm-high-threshold {
      type int64;
      description
        "High threshold alarm for Latched Min Pre FEC BER";
    }
    leaf pre-fec-ber-latched-min-alarm-low-threshold {
      type int64;
      description "Low threshold alarm for Latched Min Pre FEC BER";
    }
    leaf pre-fec-ber-latched-min-warn-high-threshold {
      type int64;
      description
        "High threshold warning for Latched Min Pre FEC
        BER";
    }
    leaf pre-fec-ber-latched-min-warn-low-threshold {
      type int64;
      description
        "Low threshold warning for Latched Min Pre FEC
        BER";
    }
    leaf pre-fec-ber-latched-max-alarm-high-threshold {
      type int64;
      description
        "High threshold alarm for Latched Max Pre FEC BER";
    }
    leaf pre-fec-ber-latched-max-alarm-low-threshold {
      type int64;
      description "Low threshold alarm for Latched Max Pre FEC BER";
    }
    leaf pre-fec-ber-latched-max-warn-high-threshold {
      type int64;
      description
        "High threshold warning for Latched Max Pre FEC
        BER";
    }
    leaf pre-fec-ber-latched-max-warn-low-threshold {
      type int64;
      description
        "Low threshold warning for Latched Max Pre FEC
        BER";
    }
    leaf pre-fec-ber-accumulated-alarm-high-threshold {
      type int64;
      description
        "High threshold alarm for Accumulated Pre FEC BER";
    }
    leaf pre-fec-ber-accumulated-alarm-low-threshold {
      type int64;
      description "Low threshold alarm for Accumulated Pre FEC BER";
    }
    leaf pre-fec-ber-accumulated-warn-high-threshold {
      type int64;
      description
        "High threshold warning for Accumulated Pre FEC
        BER";
    }
    leaf pre-fec-ber-accumulated-warn-low-threshold {
      type int64;
      description
        "Low threshold warning for Accumulated Pre FEC
        BER";
    }
    leaf pre-fec-ber-instantaneous-alarm-high-threshold {
      type int64;
      description
        "High threshold alarm for Instantaneous Pre FEC
        BER";
    }
    leaf pre-fec-ber-instantaneous-alarm-low-threshold {
      type int64;
      description
        "Low threshold alarm for Instantaneous Pre FEC
        BER";
    }
    leaf pre-fec-ber-instantaneous-warn-high-threshold {
      type int64;
      description
        "High threshold warning for Instantaneous Pre FEC
        BER";
    }
    leaf pre-fec-ber-instantaneous-warn-low-threshold {
      type int64;
      description
        "Low threshold warning for Instantaneous Pre FEC
        BER";
    }
    leaf uncorrected-ber-latched-min-alarm-high-threshold {
      type int64;
      description
        "High threshold alarm for  Latched Min
        Uncorrected BER";
    }
    leaf uncorrected-ber-latched-min-alarm-low-threshold {
      type int64;
      description
        "Low threshold alarm for  Latched Min Uncorrected
        BER";
    }
    leaf uncorrected-ber-latched-min-warn-high-threshold {
      type int64;
      description
        "High threshold warning for  Latched Min
        Uncorrected BER";
    }
    leaf uncorrected-ber-latched-min-warn-low-threshold {
      type int64;
      description
        "Low threshold alarm for Latched Min Uncorrected
        BER";
    }
    leaf uncorrected-ber-latched-max-alarm-high-threshold {
      type int64;
      description
        "High threshold alarm for Latched_Max Uncorrected
        BER";
    }
    leaf uncorrected-ber-latched-max-alarm-low-threshold {
      type int64;
      description
        "Low threshold alarm for Latched_Max Uncorrected
        BER";
    }
    leaf uncorrected-ber-latched-max-warn-high-threshold {
      type int64;
      description
        "High threshold warning Latched_Max for
        Uncorrected BER";
    }
    leaf uncorrected-ber-latched-max-warn-low-threshold {
      type int64;
      description
        "Low threshold warning Latched_Max for
        Uncorrected BER";
    }
    leaf uncorrected-ber-accumulated-alarm-high-threshold {
      type int64;
      description
        "High threshold alarm for Accumulated Uncorrected
        BER";
    }
    leaf uncorrected-ber-accumulated-alarm-low-threshold {
      type int64;
      description
        "Low threshold alarm for Accumulated Uncorrected
        BER";
    }
    leaf uncorrected-ber-accumulated-warn-high-threshold {
      type int64;
      description
        "High threshold warning for Accumulated
        Uncorrected BER";
    }
    leaf uncorrected-ber-accumulated-warn-low-threshold {
      type int64;
      description
        "Low threshold warning for Accumulated
        Uncorrected BER";
    }
    leaf uncorrected-ber-instantaneous-alarm-high-threshold {
      type int64;
      description
        "High threshold alarm for Instantaneous
        Uncorrected BER";
    }
    leaf uncorrected-ber-instantaneous-alarm-low-threshold {
      type int64;
      description
        "Low threshold alarm for Instantaneous
        Uncorrected BER";
    }
    leaf uncorrected-ber-instantaneous-warn-high-threshold {
      type int64;
      description
        "High threshold warning for Instantaneous
        Uncorrected BER";
    }
    leaf uncorrected-ber-instantaneous-warn-low-threshold {
      type int64;
      description
        "Low threshold warning for Instantaneous
        Uncorrected BER";
    }
  }

  grouping OPTICS-EXT-PARAM {
    description "extended monitored parameter information";
    leaf snr-lane1 {
      type int32;
      description "Signal to Noise Ratio on Lane 1";
    }
    leaf snr-lane2 {
      type int32;
      description "Signal to Noise Ratio on Lane 2";
    }
    leaf isi-correction-lane1 {
      type int32;
      description "Inter symbol Interference correction on Lane 1";
    }
    leaf isi-correction-lane2 {
      type int32;
      description "Inter symbol Interference correction on Lane 2";
    }
    leaf pam-rate-lane1 {
      type int32;
      description "PAM Histogram parameter on Lane 1";
    }
    leaf pam-rate-lane2 {
      type int32;
      description "PAM Histogram parameter on Lane 2";
    }
    leaf pre-fec-ber {
      type int64;
      description "Pre FEC BER since last counter reset";
    }
    leaf uncorrected-ber {
      type int64;
      description "Uncorrected BER since last counter reset";
    }
    leaf tec-current-lane1 {
      type int32;
      description
        "Current flowing to the TEC of a cooled laser on
        Lane 1";
    }
    leaf tec-current-lane2 {
      type int32;
      description
        "Current flowing to the TEC of a cooled laser on
        Lane 2";
    }
    leaf laser-diff-frequency-lane1 {
      type int32;
      description
        "Difference between target and actual center
        frequency on Lane 1";
    }
    leaf laser-diff-frequency-lane2 {
      type int32;
      description
        "Difference between target and actual center
        frequency on Lane 2";
    }
    leaf laser-diff-temperature-lane1 {
      type int32;
      description
        "Difference between target and actual temperature
        on Lane 1";
    }
    leaf laser-diff-temperature-lane2 {
      type int32;
      description
        "Difference between target and actual temperature
        on Lane 2";
    }
    leaf pre-fec-ber-latched-min {
      type int64;
      description
        "Latched minimum Pre FEC BER value since last
        read, line ingress";
    }
    leaf pre-fec-ber-latched-max {
      type int64;
      description
        "Latched maximum Pre FEC BER value since last
        read, line ingress";
    }
    leaf pre-fec-ber-accumulated {
      type int64;
      description
        "Pre FEC BER value prior accumulation period,
        line ingress";
    }
    leaf pre-fec-ber-instantaneous {
      type int64;
      description "Pre FEC BER value instantaneous line ingress";
    }
    leaf uncorrected-ber-latched-min {
      type int64;
      description
        "Latched minimum Uncorrected BER value since last
        read, line ingress";
    }
    leaf uncorrected-ber-latched-max {
      type int64;
      description
        "Latched maximum Uncorrected BER value since last
        read, line ingress";
    }
    leaf uncorrected-ber-accumulated {
      type int64;
      description
        "Uncorrected BER value prior accumulation period,
        line ingress";
    }
    leaf uncorrected-ber-instantaneous {
      type int64;
      description
        "Uncorrected BER value instantaneous line line
        ingress";
    }
  }

  grouping OPTICS-TRANSCEIVER-DATA {
    description "Optics Transceiver Details";
    leaf vendor-info {
      type string;
      description "Vendor Information";
    }
    leaf adapter-vendor-info {
      type string;
      description "Adapter Vendor Information";
    }
    leaf date {
      type string;
      description "Date in Transceiver";
    }
    leaf optics-vendor-rev {
      type string;
      description "Transceiver vendors revision number";
    }
    leaf optics-serial-no {
      type string;
      description "Transceiver serial number";
    }
    leaf optics-vendor-part {
      type string;
      description "Transceiver vendors part number";
    }
    leaf optics-type {
      type string;
      description "Transceiver optics type";
    }
    leaf vendor-name {
      type string;
      description "Transceiver optics vendor name";
    }
    leaf oui-no {
      type string;
      description "Transceiver optics type";
    }
    leaf optics-pid {
      type string;
      description "Transceiver optics pid";
    }
    leaf optics-vid {
      type string;
      description "Transceiver optics vid";
    }
    leaf connector-type {
      type Fiber-connector;
      description "Connector type";
    }
    leaf otn-application-code {
      type Otn-application-code;
      description "Otn Application Code";
    }
    leaf sonet-application-code {
      type Sonet-application-code;
      description "Sonet Application Code";
    }
    leaf ethernet-compliance-code {
      type Ethernet-pmd;
      description "Ethernet Compliance Code";
    }
    leaf internal-temperature {
      type int32;
      description "Internal Temperature in units of C";
    }
  }

  grouping OTS-EDM-ALARM-INFO {
    description "Ots Alarm Information";

    container low-tx-power {
      description "Low Tx Power in units of 0.1 dBm";
      uses OPTICS-ALARM-DETAIL;
    }

    container low-rx-power {
      description "Low Rx Power in units of 0.1 dBm";
      uses OPTICS-ALARM-DETAIL;
    }

    container rx-los-p {
      description "Rx LOS_P";
      uses OPTICS-ALARM-DETAIL;
    }

    container rx-loc {
      description "Rx LOC";
      uses OPTICS-ALARM-DETAIL;
    }

    container amp-gain-deg-low {
      description "Ampli Gain Deg Low";
      uses OPTICS-ALARM-DETAIL;
    }

    container amp-gain-deg-high {
      description "Ampli Gain Deg High";
      uses OPTICS-ALARM-DETAIL;
    }

    container auto-laser-shut {
      description "Auto Laser Shut";
      uses OPTICS-ALARM-DETAIL;
    }

    container auto-power-red {
      description "Auto Power Red";
      uses OPTICS-ALARM-DETAIL;
    }

    container auto-ampli-ctrl-disabled {
      description "Auto Ampli Ctrl Disabled";
      uses OPTICS-ALARM-DETAIL;
    }

    container auto-ampli-ctrl-config-mismatch {
      description "Auto Ampli Ctrl Config Mismatch";
      uses OPTICS-ALARM-DETAIL;
    }

    container switch-to-protect {
      description "Switch To Protect";
      uses OPTICS-ALARM-DETAIL;
    }

    container auto-ampli-ctrl-running {
      description "Auto Ampli Ctrl Running";
      uses OPTICS-ALARM-DETAIL;
    }
  }

  grouping OPTICS-ALARM-DETAIL {
    description " Optics Alarm Detail";
    leaf is-detected {
      type boolean;
      description "Is defect detected?";
    }
    leaf counter {
      type uint32;
      description "Alarm counter";
    }
  }

  grouping OPTICS-EDM-ALARM-INFO {
    description "Optics Alarm Information";

    container high-rx-power {
      description "High Rx Power in units of 0.1 dBm";
      uses OPTICS-ALARM-DETAIL;
    }

    container low-rx-power {
      description "Low Rx Power in units of 0.1 dBm";
      uses OPTICS-ALARM-DETAIL;
    }

    container high-tx-power {
      description "High Tx Power in units of 0.1 dBm";
      uses OPTICS-ALARM-DETAIL;
    }

    container low-tx-power {
      description "Low Tx Power in units of 0.1 dBm";
      uses OPTICS-ALARM-DETAIL;
    }

    container high-lbc {
      description "High laser bias current in units of percentage";
      uses OPTICS-ALARM-DETAIL;
    }

    container low-temperature {
      description "Low Temperature alarm";
      uses OPTICS-ALARM-DETAIL;
    }

    container high-temperature {
      description "High Temperature alarm";
      uses OPTICS-ALARM-DETAIL;
    }

    container low-voltage {
      description "Low Voltage alarm";
      uses OPTICS-ALARM-DETAIL;
    }

    container high-voltage {
      description "High Voltage alarm";
      uses OPTICS-ALARM-DETAIL;
    }

    container high-rx1-power {
      description "High Rx1 Power in units of 0.1 dBm";
      uses OPTICS-ALARM-DETAIL;
    }

    container high-rx2-power {
      description "High Rx2 Power in units of 0.1 dBm";
      uses OPTICS-ALARM-DETAIL;
    }

    container high-rx3-power {
      description "High Rx3 Power in units of 0.1 dBm";
      uses OPTICS-ALARM-DETAIL;
    }

    container high-rx4-power {
      description "High Rx4 Power in units of 0.1 dBm";
      uses OPTICS-ALARM-DETAIL;
    }

    container low-rx1-power {
      description "Low Rx1 Power in units of 0.1 dBm";
      uses OPTICS-ALARM-DETAIL;
    }

    container low-rx2-power {
      description "Low Rx2 Power in units of 0.1 dBm";
      uses OPTICS-ALARM-DETAIL;
    }

    container low-rx3-power {
      description "Low Rx3 Power in units of 0.1 dBm";
      uses OPTICS-ALARM-DETAIL;
    }

    container low-rx4-power {
      description "Low Rx4 Power in units of 0.1 dBm";
      uses OPTICS-ALARM-DETAIL;
    }

    container high-tx1-power {
      description "High Tx1 Power in units of 0.1 dBm";
      uses OPTICS-ALARM-DETAIL;
    }

    container high-tx2-power {
      description "High Tx2 Power in units of 0.1 dBm";
      uses OPTICS-ALARM-DETAIL;
    }

    container high-tx3-power {
      description "High Tx3 Power in units of 0.1 dBm";
      uses OPTICS-ALARM-DETAIL;
    }

    container high-tx4-power {
      description "High Tx4 Power in units of 0.1 dBm";
      uses OPTICS-ALARM-DETAIL;
    }

    container low-tx1-power {
      description "Low Tx1 Power in units of 0.1 dBm";
      uses OPTICS-ALARM-DETAIL;
    }

    container low-tx2-power {
      description "Low Tx2 Power in units of 0.1 dBm";
      uses OPTICS-ALARM-DETAIL;
    }

    container low-tx3-power {
      description "Low Tx3 Power in units of 0.1 dBm";
      uses OPTICS-ALARM-DETAIL;
    }

    container low-tx4-power {
      description "Low Tx4 Power in units of 0.1 dBm";
      uses OPTICS-ALARM-DETAIL;
    }

    container high-tx1lbc {
      description
        "High Tx1 laser bias current in units of
        percentage";
      uses OPTICS-ALARM-DETAIL;
    }

    container high-tx2lbc {
      description
        "High Tx2 laser bias current in units of
        percentage";
      uses OPTICS-ALARM-DETAIL;
    }

    container high-tx3lbc {
      description
        "High Tx3 laser bias current in units of
        percentage";
      uses OPTICS-ALARM-DETAIL;
    }

    container high-tx4lbc {
      description
        "High Tx4 laser bias current in units of
        percentage";
      uses OPTICS-ALARM-DETAIL;
    }

    container low-tx1lbc {
      description
        "Low Tx1 laser bias current in units of
        percentage";
      uses OPTICS-ALARM-DETAIL;
    }

    container low-tx2lbc {
      description
        "Low Tx2 laser bias current in units of
        percentage";
      uses OPTICS-ALARM-DETAIL;
    }

    container low-tx3lbc {
      description
        "Low Tx3 laser bias current in units of
        percentage";
      uses OPTICS-ALARM-DETAIL;
    }

    container low-tx4lbc {
      description
        "Low Tx4 laser bias current in units of
        percentage";
      uses OPTICS-ALARM-DETAIL;
    }

    container rx-los {
      description "RX LOS";
      uses OPTICS-ALARM-DETAIL;
    }

    container tx-los {
      description "TX LOS";
      uses OPTICS-ALARM-DETAIL;
    }

    container rx-lol {
      description "RX LOL";
      uses OPTICS-ALARM-DETAIL;
    }

    container tx-lol {
      description "TX LOL";
      uses OPTICS-ALARM-DETAIL;
    }

    container tx-fault {
      description "TX Fault";
      uses OPTICS-ALARM-DETAIL;
    }

    container hidgd {
      description "HI DGD";
      uses OPTICS-ALARM-DETAIL;
    }

    container oorcd {
      description "OOR CD";
      uses OPTICS-ALARM-DETAIL;
    }

    container osnr {
      description "OSNR";
      uses OPTICS-ALARM-DETAIL;
    }

    container wvlool {
      description "WVL OOL";
      uses OPTICS-ALARM-DETAIL;
    }

    container mea {
      description "MEA";
      uses OPTICS-ALARM-DETAIL;
    }

    container imp-removal {
      description "IMPROPER REM";
      uses OPTICS-ALARM-DETAIL;
    }

    container rx-loc {
      description "Rx LOC";
      uses OPTICS-ALARM-DETAIL;
    }

    container amp-gain-deg-low {
      description "Ampli Gain Deg Low";
      uses OPTICS-ALARM-DETAIL;
    }

    container amp-gain-deg-high {
      description "Ampli Gain Deg High";
      uses OPTICS-ALARM-DETAIL;
    }

    container txpwr-mismatch {
      description "TX POWER PROV MISMATCH";
      uses OPTICS-ALARM-DETAIL;
    }
  }

  grouping LANE-ALARM-DETAIL {
    description " Lane Alarm Detail";
    leaf is-detected {
      type boolean;
      description "Is defect detected?";
    }
    leaf counter {
      type uint32;
      description "Alarm counter";
    }
  }

  grouping LANE-EDM-ALARM-INFO {
    description " Lane Information Detail";

    container high-rx-power {
      description "High Rx Power";
      uses LANE-ALARM-DETAIL;
    }

    container low-rx-power {
      description "Low Rx Power";
      uses LANE-ALARM-DETAIL;
    }

    container high-tx-power {
      description "High Tx Power";
      uses LANE-ALARM-DETAIL;
    }

    container low-tx-power {
      description "Low Tx Power";
      uses LANE-ALARM-DETAIL;
    }

    container high-lbc {
      description "High laser bias current";
      uses LANE-ALARM-DETAIL;
    }
  }

  grouping OPTICS-EDM-LANE-DATA {
    description "Grey lane data";

    container lane-alarm-info {
      description "Lane Alarm Information";
      uses LANE-EDM-ALARM-INFO;
    }
    leaf lane-index {
      type uint32;
      description "The index number of the lane";
    }
    leaf laser-bias-current-percent {
      type uint32;
      units "percentage";
      description "Laser Bias Current in units of 0.01 percentage";
    }
    leaf laser-bias-current-milli-amps {
      type uint32;
      description "Laser Bias Current in units of 0.01mA";
    }
    leaf transmit-power {
      type int32;
      description "Transmit power in the units of 0.01dBm";
    }
    leaf receive-power {
      type int32;
      description
        "Transponder receive power in the units of 0
        .01dBm";
    }
    leaf receive-signal-power {
      type int32;
      description
        "Transponder receive signal power in the units of
        0.01dBm";
    }
    leaf transmit-signal-power {
      type int32;
      description "Transmit Signal power in the units of 0.01dBm";
    }
    leaf output-frequency {
      type int32;
      description
        "Output frequency read from hw in the units of
        100MHz";
    }
    leaf frequency-offset {
      type int32;
      description "Frequency Offset read from hw in units of MHz";
    }
  }

  grouping OPTICS-EDM-NETWORK-SRLG-STRUCTURE {
    description "Network SRLG Information";
    leaf set-number {
      type uint32;
      description "Array to maintain set number";
    }
    leaf-list network-srlg {
      type uint32;
      description "Network Srlg";
    }
  }

  grouping OPTICS-EDM-NETWORK-SRLG-INFO {
    description "Network SRLG Information Array";

    list network-srlg-array {
      description "Network Srlg Array";
      uses OPTICS-EDM-NETWORK-SRLG-STRUCTURE;
    }
  }

  grouping OPTICS-EDM-INFO {
    description "optics transponder information";

    container network-srlg-info {
      description "Network SRLG information";
      uses OPTICS-EDM-NETWORK-SRLG-INFO;
    }

    container optics-alarm-info {
      description "Optics Alarm Information";
      uses OPTICS-EDM-ALARM-INFO;
    }

    container ots-alarm-info {
      description "Ots Alarm Information";
      uses OTS-EDM-ALARM-INFO;
    }

    container transceiver-info {
      description "Transceiver Vendor Details";
      uses OPTICS-TRANSCEIVER-DATA;
    }

    container ext-param-val {
      description "Extended optics parameters";
      uses OPTICS-EXT-PARAM;
    }

    container ext-param-threshold-val {
      description "Extended optics parameters threshold values";
      uses OPTICS-EXT-THRESHOLD-PARAM;
    }

    container extended-alarm-alarm-info {
      description "Extended DOM alarm Information";
      uses EXT-PARAM-EDM-ALARM-INFO;
    }

    container ains-info {
      description "AINS information";
      uses OPTICS-AINS-HW-INFO;
    }
    leaf transport-admin-state {
      xr:event-telemetry "Subscribe Telemetry Event";
      type Optics-tas;
      description "Transport Admin State";
    }
    leaf optics-present {
      type boolean;
      description "Is Optics Present?";
    }
    leaf optics-type {
      type Optics;
      description "Old Optics type name, Use Derived Optics type";
    }
    leaf derived-optics-type {
      type string;
      description "Derived Optics type name";
    }
    leaf optics-module {
      type string;
      description "Optics module name";
    }
    leaf dwdm-carrier-band {
      type Optics-wave-band;
      description "DWDM Carrier Band information";
    }
    leaf dwdm-carrier-channel {
      type string;
      description "Current ITU DWDM Carrier channel number";
    }
    leaf dwdm-carrier-frequency {
      type string;
      description
        "DWDM Carrier frequency read from hw in the units
        of  1THz";
    }
    leaf dwdm-carrier-wavelength {
      type string;
      description "Wavelength of color optics 0.001nm";
    }
    leaf grey-wavelength {
      type uint32;
      description "Wavelength of grey optics 0.01nm";
    }
    leaf rx-low-threshold {
      type int32;
      description "Rx Low threshold value in units of 0.1dBm";
    }
    leaf rx-high-threshold {
      type int32;
      description "Rx High threshold value in units of 0.1dBm";
    }
    leaf lbc-high-threshold {
      type int32;
      units "percentage";
      description "LBC High threshold value in units of percentage";
    }
    leaf tx-low-threshold {
      type int32;
      description "Tx Low threshold value in units of 0.1dBm";
    }
    leaf tx-high-threshold {
      type int32;
      description "Tx High threshold value in units of 0.1dBm";
    }
    leaf lbc-th-high-default {
      type int32;
      description
        "LBC high threshold default value in units of 0
        .001mA";
    }
    leaf lbc-th-low-default {
      type int32;
      description
        "LBC low threshold default value in units of 0
        .001mA";
    }
    leaf temp-low-threshold {
      type int32;
      description "Temp Low threshold value in the units 0.01C";
    }
    leaf temp-high-threshold {
      type int32;
      description "Temp High threshold value in the units of 0.01C";
    }
    leaf volt-low-threshold {
      type int32;
      description "Volt Low threshold value in the units of 0.01V";
    }
    leaf volt-high-threshold {
      type int32;
      description "Volt High threshold value in the units of 0.01V";
    }
    leaf cd {
      type int32;
      description "Chromatic Dispersion ps/nm";
    }
    leaf cd-min {
      type int32;
      description "Chromatic Dispersion Min ps/nm";
    }
    leaf cd-max {
      type int32;
      description "Chromatic Dispersion Max ps/nm";
    }
    leaf cd-low-threshold {
      type int32;
      description "Chromatic Dispersion low threshold ps/nm";
    }
    leaf cd-high-threshold {
      type int32;
      description "Chromatic Dispersion high threshold ps/nm";
    }
    leaf osnr-low-threshold {
      type string;
      description "OSNR low threshold in 0.01 dB";
    }
    leaf dgd-high-threshold {
      type string;
      description "DGD high threshold in 0.1 ps";
    }
    leaf polarization-mode-dispersion {
      type string;
      description "Polarization Mode Dispersion 0.1ps";
    }
    leaf second-order-polarization-mode-dispersion {
      type string;
      description
        "Second Order Polarization Mode Dispersion 0
        .1ps^2";
    }
    leaf optical-signal-to-noise-ratio {
      type string;
      description "Optical Signal to Noise Ratio dB";
    }
    leaf polarization-dependent-loss {
      type string;
      description "Polarization Dependent Loss dB";
    }
    leaf polarization-change-rate {
      type string;
      description "Polarization Change Rate rad/s";
    }
    leaf differential-group-delay {
      type string;
      description "Differential Group Delay ps";
    }
    leaf phase-noise {
      type string;
      description "Phase Noise dB";
    }
    leaf pm-enable {
      type uint32;
      description "PmEable or Disable";
    }
    leaf laser-state {
      type Optics-laser-state;
      description "Showing laser state.Either ON or OFF or unknown";
    }
    leaf modulation-type {
      type Optics-modulation;
      description "Available Modulation Types";
    }
    leaf led-state {
      type Optics-led-state;
      description "Showing Current Colour of led state";
    }
    leaf controller-state {
      xr:event-telemetry "Subscribe Telemetry Event";
      type Optics-controller-state;
      description
        "Optics controller state: Up, Down or
        Administratively Down";
    }
    leaf form-factor {
      type Optics-form-factor;
      description "Optics form factor";
    }
    leaf phy-type {
      type Optics-phy;
      description "Optics physical type";
    }
    leaf cfg-tx-power {
      type int32;
      description "Configured Tx power value in units of 0.1dB";
    }
    leaf cfg-tx-power-configurable {
      type boolean;
      description "TX Power Configuration is supported or not";
    }
    leaf temperature {
      type int32;
      description "Temperature value in units of 0.01 C";
    }
    leaf voltage {
      type int32;
      description "Voltage value in units of 0.01V";
    }
    leaf display-volt-temp {
      type boolean;
      description "Display Volt/Temp ?";
    }
    leaf cd-configurable {
      type boolean;
      description "CD Configurable is supported or not";
    }
    leaf optics-fec {
      type Optics-fec;
      description "Optics FEC";
    }
    leaf skip-snmp-pm-table {
      type int32;
      description "PM enabled or not";
    }
    leaf port-type {
      type Optics-port;
      description "Showing port type";
    }
    leaf port-status {
      type Optics-port-status;
      description "Showing port status";
    }
    leaf rx-voa-attenuation {
      type int32;
      description "Rx Voa Attenuation in the units of 0.01dBm";
    }
    leaf tx-voa-attenuation {
      type int32;
      description "Tx Voa Attenuation in the units of 0.01dBm";
    }
    leaf ampli-gain {
      type int32;
      description "Ampli Gain in the units of 0.01dBm";
    }
    leaf ampli-tilt {
      type int32;
      description "Ampli Tilt in the units of 0.01dBm";
    }
    leaf rx-power-th-configurable {
      type boolean;
      description "rx power th configurable";
    }
    leaf tx-power-th-configurable {
      type boolean;
      description "tx power th configurable";
    }
    leaf rx-voa-attenuation-config-val {
      type int32;
      description
        "RX VOA attenuation configured value in units of
        0.1dB";
    }
    leaf tx-voa-attenuation-config-val {
      type int32;
      description
        "TX VOA attenuation configured value in units of
        0.1dB";
    }
    leaf ampli-control-mode-config-val {
      type Optics-amplifier-control-mode;
      description "ampli control mode config val";
    }
    leaf ampli-gain-range-config-val {
      type Optics-amplifier-gain-range;
      description "ampli gain range config val";
    }
    leaf ampli-gain-config-val {
      type int32;
      description "Ampli gain configured value in units of 0.1dB";
    }
    leaf ampli-tilt-config-val {
      type int32;
      description "Ampli tilt configured value in units of 0.1dB";
    }
    leaf ampli-channel-power-config-val {
      type int32;
      description
        "Ampli channel power configured value in units of
        0.1dBm";
    }
    leaf channel-power-max-delta-config-val {
      type int32;
      description
        "Channel power max delta configured value in
        units of 0.1 dBm";
    }
    leaf ampli-gain-thr-deg-low-config-val {
      type int32;
      description
        "Ampli gain low degrade threshold configured
        value in units of 0.1dBm";
    }
    leaf ampli-gain-thr-deg-high-config-val {
      type int32;
      description
        "Ampli gain high degrade threshold configured
        value in units of 0.1dBm";
    }
    leaf osri-config-val {
      type boolean;
      description "osri config val";
    }
    leaf tx-config-val {
      type boolean;
      description "tx config val";
    }
    leaf rx-config-val {
      type boolean;
      description "rx config val";
    }
    leaf safety-control-mode-config-val {
      type Optics-amplifier-safety-control-mode;
      description "safety control mode config val";
    }
    leaf total-rx-power {
      type int32;
      description
        "Total Receive Power for Multi-Lane Optics in
        units of 0.01 dBm";
    }
    leaf total-tx-power {
      type int32;
      description
        "Total Transmit Power for Multi-Lane Optics in
        units of 0.01 dBm";
    }
    leaf is-bo-configured {
      type boolean;
      description "Is BO configured ?";
    }
    leaf is-ext-param-valid {
      type boolean;
      description "Are the Extended Parameters Valid ?";
    }
    leaf alarm-detected {
      type boolean;
      description "Are there any alarms ?";
    }
    leaf rx-low-warning-threshold {
      type int32;
      description
        "Rx Low Warning threshold value in units of 0
        .1dBm";
    }
    leaf rx-high-warning-threshold {
      type int32;
      description
        "Rx High Warning threshold value in units of 0
        .1dBm";
    }
    leaf tx-low-warning-threshold {
      type int32;
      description
        "Tx Low Warning threshold value in units of 0
        .1dBm";
    }
    leaf tx-high-warning-threshold {
      type int32;
      description
        "Tx High Warning threshold value in units of 0
        .1dBm";
    }
    leaf lbc-th-high-warning-default {
      type int32;
      description
        "LBC high Warning threshold default value in
        units of 0.001mA";
    }
    leaf lbc-th-low-warning-default {
      type int32;
      description
        "LBC low warning threshold default value in units
        of 0.001mA";
    }
    leaf temp-low-warning-threshold {
      type int32;
      description
        "Temp Low warning threshold value in the units 0
        .01C";
    }
    leaf temp-high-warning-threshold {
      type int32;
      description
        "Temp High warning threshold value in the units
        of 0.01C";
    }
    leaf volt-low-warning-threshold {
      type int32;
      description
        "Volt Low warning threshold value in the units of
        0.01V";
    }
    leaf volt-high-warning-threshold {
      type int32;
      description
        "Volt High warning threshold value in the units
        of 0.01V";
    }
    leaf description {
      type string;
      description "Controller description string";
    }
    leaf ampli-gain-range {
      type Optics-amplifier-gain-range;
      description "Ampli gain range";
    }
    leaf safety-control-mode {
      type Optics-amplifier-safety-control-mode;
      description "Safety control mode";
    }
    leaf osri {
      type boolean;
      description "OSRI";
    }
    leaf tx-enable {
      type boolean;
      description "TX Enable";
    }
    leaf rx-enable {
      type boolean;
      description "RX Enable";
    }
    leaf is-optics-type-string-valid {
      type boolean;
      description "Is the Optics type string valid ?";
    }
    leaf optics-type-str {
      type string;
      description "optics type String";
    }
    leaf rx-low-threshold-current {
      type int32;
      description
        "Rx Low threshold actual value in units of 0.1dBm";
    }
    leaf rx-span-loss {
      type int32;
      description "RX Span Loss in units of 0.01 dB";
    }
    leaf tx-span-loss {
      type int32;
      description "TX Span Loss in units of 0.01 dB";
    }
    leaf baud-rate {
      type string;
      description "Baud Rate in GBd";
    }
    leaf bits-per-symbol {
      type string;
      description "Bits per Symbol";
    }

    list lane-data {
      description "Lane information";
      uses OPTICS-EDM-LANE-DATA;
    }
  }

  grouping OTS-EDM-SPECTRUM-POWER-INFO {
    description "OTS EDM SPECTRUM POWER INFO";
    leaf slice-num {
      type uint32;
      description "spectrum slice number";
    }
    leaf lower-frequency {
      type uint64;
      description "Lower frequency of the specified PSD";
    }
    leaf upper-frequency {
      type uint64;
      description "Upper frequency of the specified PSD";
    }
    leaf rx-power {
      type int32;
      description "Received Power in dBm multiplied by 100";
    }
    leaf tx-power {
      type int32;
      description "Transmit Power in dBm multiplied by 100";
    }
    leaf rx-psd {
      type string {
        length "0..16";
      }
      description
        "Received Power spectral density in microwatts
        per megahertz, uW/MHz";
    }
    leaf tx-psd {
      type string {
        length "0..16";
      }
      description
        "Transmit Power spectral density in microwatts
        per megahertz, uW/MHz";
    }
  }

  grouping OTS-EDM-SPECTRUM-INFO {
    description "power information of slices in optical spectrum";
    leaf total-spectrum-slice-count {
      type uint32;
      description "Total number of slices in Spectrum";
    }
    leaf spectrum-slice-spacing {
      type uint32;
      description "Spacing between spectrum slices";
    }
    leaf first-slice-wavelength {
      type string {
        length "0..32";
      }
      description "Wavelength of first slice";
    }

    list spectrum-slice-power-info {
      description "Power information of spectrum slice info";
      uses OTS-EDM-SPECTRUM-POWER-INFO;
    }
  }

  grouping OPTICS-EDM-SPECTRUM-INFO {
    description "optics spectrum information";

    container spectrum-info {
      description "OTS Spectrum information";
      uses OTS-EDM-SPECTRUM-INFO;
    }
  }

  grouping OPTICS-EDM-CHANNEL-WAVELENGTH-MAP-INFO {
    description "OPTICS EDM CHANNEL WAVELENGTH MAP INFO";
    leaf itu-chan-num {
      type uint32;
      description "ITU channel number";
    }
    leaf g694-chan-num {
      type int32;
      description "G694 channel number";
    }
    leaf frequency {
      type string {
        length "0..32";
      }
      description "Frequency";
    }
    leaf wavelength {
      type string {
        length "0..32";
      }
      description "Wavelength";
    }
  }

  grouping OPTICS-EDM-WAVE-INFO {
    description "wavelength channel mapping information";
    leaf dwdm-carrier-band {
      type Optics-wave-band;
      description "DWDM carrier band";
    }
    leaf dwdm-carrier-min {
      type uint32;
      description "Lowest DWDM carrier supported";
    }
    leaf dwdm-carrier-max {
      type uint32;
      description "Highest DWDM carrier supported";
    }

    list dwdm-carrier-map-info {
      description "DWDM carrier mapping info";
      uses OPTICS-EDM-CHANNEL-WAVELENGTH-MAP-INFO;
    }
  }
}
