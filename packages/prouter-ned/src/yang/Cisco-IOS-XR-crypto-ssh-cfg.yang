module Cisco-IOS-XR-crypto-ssh-cfg {

  /*** NAMESPACE / PREFIX DEFINITION ***/

  namespace "http://cisco.com/ns/yang/Cisco-IOS-XR-crypto-ssh-cfg";


  prefix "crypto-ssh-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR crypto-ssh package configuration.

     This module contains definitions
     for the following management objects:
       ssh: Secure Shell configuration

     Copyright (c) 2013-2018 by Cisco Systems, Inc.
     All rights reserved.";

  revision "2018-05-24" {
    description
      "Changes in enable cipher aes-cbc schema and added enable cipher 3des-cbc support";
  }

  revision "2018-04-04" {
    description
      "Changes in ssh kexchange algorithms schema";
  }

  revision "2017-11-21" {
    description
      "Resolving dependency issue with SAM";
  }

  revision "2017-07-15" {
    description
      "Fixing client rekey support.";
  }

  revision "2017-05-01" {
    description
      "Fixing backward compatibility error in module.";
  }

  revision "2015-07-30" {
    description
      "Descriptions updated.";
  }

  revision "2015-07-13" {
    description
      "IOS XR 5.3.2 revision.";
  }

  revision "2015-01-07" {
    description
      "IOS XR 5.3.1 revision.";
  }


  grouping VRF {
    description "Common node of vrf-table, netconf-vrf-table";

    list vrf {
      key "vrf-name";
      description "Enter VRF name";
      leaf vrf-name {
        type xr:Cisco-ios-xr-string {
          length "1..32";
        }
        description "Enter VRF name";
      }
      leaf enable {
        type empty;
        mandatory true;
        description "Enable to use VRF";
      }
      leaf ipv4-access-list {
        type xr:Cisco-ios-xr-string {
          length "1..32";
        }
        description "SSH v4 access-list name";
      }
      leaf ipv6-access-list {
        type xr:Cisco-ios-xr-string {
          length "1..32";
        }
        description "SSH v6 access-list name";
      }
    }
  }

  grouping KEY-EXCHANGE {
    description "Common node of client-algo, server-algo";

    container key-exchanges {
      description "Key exchange algorithm";
      leaf-list key-exchange {
        type string {
          length "1..32";
        }
        max-elements "5";
        description "key exchange algorithm";
      }
    }
  }

  container ssh {
    description "Secure Shell configuration";

    container client {
      description "Provide SSH client service";

      container client-algo {
        description "Cisco ssh algorithms";
        uses KEY-EXCHANGE;
      }

      container client-enable {
        description "clientenable";

        container client-cipher {
          description "Enable AES-CBC and 3DES_CBC for ssh client";
          leaf aes-cbc {
            type boolean;
            default "false";
            description "Enable AES-CBC ciphers";
          }
          leaf tripledes-cbc {
            type boolean;
            default "false";
            description "Enable 3DES-CBC cipher";
          }
        }
      }
      leaf rekey-volume {
        type uint32 {
          range "1024..4095";
        }
        default "1024";
        description "Configure client volume-based rekey for SSH";
      }
      leaf host-public-key {
        type string;
        description "Filename - where to store known host file";
      }
      leaf client-vrf {
        type xr:Cisco-ios-xr-string {
          length "1..32";
        }
        description "Source interface VRF for ssh client sessions";
      }
      leaf rekey-time {
        type uint32 {
          range "30..1440";
        }
        units "minute";
        default "60";
        description "Configure client time-based rekey for SSH";
      }
      leaf source-interface {
        type xr:Interface-name;
        description "Source interface for ssh client sessions";
      }
      leaf dscp {
        type uint32 {
          range "0..63";
        }
        description "Cisco sshd DSCP value";
      }
    }

    container server {
      description "Provide SSH server service";

      container disable {
        description "disable";

        container hmac {
          description "hmac";
          leaf hmac-sha512 {
            type boolean;
            default "false";
            description "Disable Hmac-sha2-512 negotiation";
          }
        }
      }

      container enable {
        description "enable";

        container cipher {
          description "Enable AES-CBC and 3DES-CBC ciphers";
          leaf aes-cbc {
            type boolean;
            default "false";
            description "Enable aes-cbc ciphers";
          }
          leaf tripledes-cbc {
            type boolean;
            default "false";
            description "Enable 3des-cbc cipher";
          }
        }
      }

      container vrf-table {
        description "Cisco sshd VRF name";
        uses VRF;
      }

      container server-algo {
        description "Cisco ssh algorithms";
        uses KEY-EXCHANGE;
      }

      container capability {
        description "Capability";
        leaf netconf-xml {
          type boolean;
          default "false";
          description "Enable Netconf-XML stack on port 22";
        }
      }

      container netconf-vrf-table {
        description "Cisco sshd Netconf VRF name";
        uses VRF;
      }
      leaf rekey-volume {
        type uint32 {
          range "1024..4095";
        }
        default "1024";
        description "Configure volume-based rekey for SSH";
      }
      leaf session-limit {
        type uint32 {
          range "1..110";
        }
        description "Cisco sshd session-limit of service requests";
      }
      leaf netconf {
        type uint32 {
          range "1..65535";
        }
        default "830";
        description
          "port number on which ssh service to be started
          for netconf";
      }
      leaf v2 {
        type empty;
        description "Cisco sshd force protocol version 2 only";
      }
      leaf rekey-time {
        type uint32 {
          range "30..1440";
        }
        units "minute";
        default "60";
        description "Time Period in minutes, defalut 60";
      }
      leaf logging {
        type empty;
        description "Enable ssh server logging";
      }
      leaf rate-limit {
        type uint32 {
          range "1..600";
        }
        default "60";
        description "Cisco sshd rate-limit of service requests";
      }
      leaf timeout {
        type uint32 {
          range "5..120";
        }
        units "second";
        default "30";
        description
          "Timeout value between 5-120 seconds defalut 30";
      }
      leaf dscp {
        type uint32 {
          range "0..63";
        }
        description "Cisco sshd DSCP value";
      }
    }
  }
}
