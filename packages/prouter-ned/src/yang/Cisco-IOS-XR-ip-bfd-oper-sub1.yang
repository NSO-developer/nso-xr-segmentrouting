submodule Cisco-IOS-XR-ip-bfd-oper-sub1 {

  belongs-to Cisco-IOS-XR-ip-bfd-oper {
    prefix Cisco-IOS-XR-ip-bfd-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ip-bfd package operational data.

     Copyright (c) 2013-2018 by Cisco Systems, Inc.
     All rights reserved.";

  revision "2017-09-07" {
    description
      "Fixed type translation error.";
  }

  revision "2015-11-09" {
    description
      "IOS XR 6.0 revision.";
  }

  typedef Bfd-mp-download-state {
    type enumeration {
      enum bfd-mp-download-none {
        value 0;
        description "bfd mp download none";
      }
      enum bfd-mp-download-no-lc {
        value 1;
        description "bfd mp download no lc";
      }
      enum bfd-mp-download-downloaded {
        value 2;
        description "bfd mp download downloaded";
      }
      enum bfd-mp-download-ack {
        value 3;
        description "bfd mp download ack";
      }
      enum bfd-mp-download-nack {
        value 4;
        description "bfd mp download nack";
      }
      enum bfd-mp-download-delete {
        value 5;
        description "bfd mp download delete";
      }
    }
    description "Bfd mp download state";
  }
  typedef Bfd-mgmt-session-diag {
    type enumeration {
      enum bfd-mgmt-session-diag-none {
        value 0;
        description "No diagnostic";
      }
      enum bfd-mgmt-session-diag-control-detect-expired {
        value 1;
        description "Control Detection Time Expired";
      }
      enum bfd-mgmt-session-diag-echo-function-failed {
        value 2;
        description "Echo Function Failed";
      }
      enum bfd-mgmt-session-diag-nb-or-signaled-down {
        value 3;
        description "Neighbor Signaled Session Down";
      }
      enum bfd-mgmt-session-diag-fwding-plane-reset {
        value 4;
        description "Forwarding Plane Reset";
      }
      enum bfd-mgmt-session-diag-path-down {
        value 5;
        description "Path Down";
      }
      enum bfd-mgmt-session-diag-conc-path-down {
        value 6;
        description "Concatenated Path Down";
      }
      enum bfd-mgmt-session-diag-admin-down {
        value 7;
        description "Administratively Down";
      }
      enum bfd-mgmt-session-diag-rev-conc-path-down {
        value 8;
        description "Reverse Concatenated Path Down";
      }
      enum bfd-mgmt-session-diag-num {
        value 10;
        description "Unknown diagnostic state";
      }
    }
    description "BFD session diagnostic";
  }
  typedef Bfd-in6-addr {
    type inet:ipv6-address;
    description "Bfd in6 addr";
  }
  typedef Bfd-in-addr {
    type inet:ipv4-address;
    description "Bfd in addr";
  }
  typedef Bfd-af-id {
    type enumeration {
      enum bfd-af-id-none {
        value 0;
        description "No Address";
      }
      enum bfd-af-id-ipv4 {
        value 2;
        description "IPv4 AFI";
      }
      enum bfd-af-id-ipv6 {
        value 10;
        description "IPv6 AFI";
      }
    }
    description "Bfd af id";
  }
  typedef Bfd-discr {
    type uint32;
    description "Bfd discr";
  }
  typedef Bfd-mgmt-pkt-display {
    type enumeration {
      enum bfd-mgmt-pkt-display-type-none {
        value 0;
        description "None";
      }
      enum bfd-mgmt-pkt-display-type-bob-mbr {
        value 1;
        description "Display Type Bundle RTR Member";
      }
      enum bfd-mgmt-pkt-display-type-max {
        value 2;
        description "Display Type Enum Max Value";
      }
    }
    description "BFD session type";
  }
  typedef Bfd-session {
    type enumeration {
      enum undefined {
        description "Session type is undefined";
      }
      enum bundle-member {
        description "Session type is bundle member";
      }
      enum bundle-interface {
        description "Session type is bundle interface";
      }
      enum state-inheriting {
        description "Session type is state inheriting";
      }
      enum bundle-vlan {
        description "Session type is bundle vlan";
      }
      enum mpls-tp {
        description "Session type is MPLS-TP";
      }
      enum gre {
        description "Session type is GRE tunnel";
      }
      enum pseudowire-headend {
        description "Session type is PW-HE";
      }
      enum ip-single-hop {
        description "Session type is IP single hop";
      }
    }
    description "BFD session type";
  }
  typedef Bfd-mgmt-session-state {
    type enumeration {
      enum bfd-mgmt-session-state-admin-down {
        value 0;
        description "Session in Administratively Shutdown State";
      }
      enum bfd-mgmt-session-state-down {
        value 1;
        description "Session in Down State";
      }
      enum bfd-mgmt-session-state-init {
        value 2;
        description "Session in Initializing State";
      }
      enum bfd-mgmt-session-state-up {
        value 3;
        description "Session in Up State";
      }
      enum bfd-mgmt-session-state-failing {
        value 4;
        description "Session in Failing State";
      }
      enum bfd-mgmt-session-state-unknown {
        value 6;
        description "Session in Unknown State";
      }
    }
    description "BFD session states";
  }

  grouping BFD-MGMT-RELATION-LINK-DETAIL {
    description "Detail Member Link Information";
    leaf state {
      type Bfd-mgmt-session-state;
      description "State";
    }
    leaf interface-name {
      type string {
        length "0..64";
      }
      description "Session Interface Name";
    }
    leaf local-discriminator {
      type Bfd-discr;
      description "Session's Local discriminator";
    }
  }

  grouping BFD-MGMT-RELATION {
    description "BFD Relation Detail Information";
    leaf state {
      type Bfd-mgmt-session-state;
      description "State";
    }
    leaf local-discriminator {
      type Bfd-discr;
      description "Session's Local discriminator";
    }

    list link-information {
      description "Detail Member Link Information";
      uses BFD-MGMT-RELATION-LINK-DETAIL;
    }

    list association-information {
      description "Association session information";
      uses BFD-MGMT-SESSION-ASSOCIATION-INFORMATION;
    }
  }

  grouping BFD-MGMT-RELATION-LINK-BRIEF {
    description "Brief Member Link Information";
    leaf state {
      type Bfd-mgmt-session-state;
      description "State";
    }
    leaf interface-name {
      type string {
        length "0..64";
      }
      description "Session Interface Name";
    }
  }

  grouping BFD-MGMT-RELATION-BRIEF {
    description "BFD Relation Brief Information";
    leaf state {
      type Bfd-mgmt-session-state;
      description "State";
    }

    list link-information {
      description "Brief Member Link Information";
      uses BFD-MGMT-RELATION-LINK-BRIEF;
    }
  }

  grouping BFD-MGMT-MIB-DATABASE {
    description "BFD MIB Mapping Database Entry Information";

    container dest-address {
      description "Session Destination address";
      uses IP-ADDR-T-UNION;
    }
    leaf local-discriminator {
      type Bfd-discr;
      description "Sessions' Local Discriminator";
    }
    leaf remote-discriminator {
      type Bfd-discr;
      description "Sessions' Remote Discriminator";
    }
    leaf sessionversion {
      type uint32;
      description "Session BFD Version";
    }
    leaf session-state {
      type uint32;
      description "Session State";
    }
    leaf trap-bitmap {
      type uint32;
      description "Trap Generator Bitmap";
    }
    leaf pkt-in {
      type uint64;
      description "Packet In Counter";
    }
    leaf pkt-out {
      type uint64;
      description "Packet Out Counter";
    }
    leaf last-up-time-sec {
      type uint64;
      units "second";
      description "Last Session Up Time (seconds)";
    }
    leaf last-up-time-nsec {
      type uint32;
      units "nanosecond";
      description "Last Session Up Time (nanoseconds)";
    }
    leaf last-down-time-sec {
      type uint64;
      units "second";
      description "Last Session Down Time (seconds)";
    }
    leaf last-down-time-nsec {
      type uint32;
      units "nanosecond";
      description "Last Session Down Time (nanoseconds)";
    }
    leaf last-io-evm-schd-time-sec {
      type uint64;
      units "second";
      description "Last IO EVM Schd Time (seconds)";
    }
    leaf last-io-evm-schd-time-nsec {
      type uint32;
      units "nanosecond";
      description "Last IO Evm Schd Time (nanoseconds)";
    }
    leaf last-io-evm-schd-comp-time-sec {
      type uint64;
      units "second";
      description "Last IO EVM Schd Comp Time (seconds)";
    }
    leaf last-io-evm-schd-comp-time-nsec {
      type uint32;
      units "nanosecond";
      description "Last IO Evm Schd Comp Time (nanoseconds)";
    }
    leaf last-down-diag {
      type Bfd-mgmt-session-diag;
      description "Last Session Down Diag";
    }
    leaf last-rx-down-diag {
      type Bfd-mgmt-session-diag;
      description "Last Rx Session Down Diag";
    }
    leaf up-counter {
      type uint32;
      description "Up Count";
    }
    leaf last-time-cached {
      type uint64;
      description "Last Time Session Info Queried";
    }
    leaf interface-name {
      type string {
        length "0..64";
      }
      description "Session Interface Name";
    }
    leaf int-handle {
      type uint32;
      description "Session Interface Handle";
    }
    leaf detection-multiplier {
      type uint32;
      description "Detection Multiplier";
    }
    leaf desired-min-tx-interval {
      type uint32;
      description "Desired Min TX Interval";
    }
    leaf required-min-rx-interval {
      type uint32;
      description "Required Min RX Interval";
    }
    leaf required-min-rx-echo-interval {
      type uint32;
      description "Required Min RX Echo Interval";
    }
  }

  grouping BFD-LOC-MGMT-SESSION-STATE-INFORMATION {
    description "BFD Location Session State Information";
    leaf total-count {
      type uint32;
      description "Number of sessions in database";
    }
    leaf up-count {
      type uint32;
      description "Number of sessions in up state";
    }
    leaf down-count {
      type uint32;
      description "Number of sessions in down state";
    }
    leaf unknown-count {
      type uint32;
      description "Number of sessions in unknown state";
    }
    leaf retry-count {
      type uint32;
      description "Number of sessions in retry state";
    }
    leaf standby-count {
      type uint32;
      description "Number of sessions in standby state";
    }
  }

  grouping BFD-MGMT-BFD-LOC-INFORMATION {
    description "BFD Location Summary Information";

    container session-state {
      description "Statistics of states for sessions";
      uses BFD-LOC-MGMT-SESSION-STATE-INFORMATION;
    }
  }

  grouping BFD-MGMT-SUMMARY {
    description "BFD MGMT SUMMARY";
    leaf node-id {
      type xr:Node-id;
      description "Node ID";
    }
    leaf pps-allocated-value {
      type uint32;
      description "Allocated PPS value";
    }
    leaf ppsmp-allocated-value {
      type uint32;
      description "Allocated MP PPS value";
    }
    leaf pps-max-value {
      type uint32;
      description "Max PPS value";
    }
    leaf ppsmp-max-value {
      type uint32;
      description "Max MP PPS value";
    }
    leaf total-session-number {
      type uint32;
      description "Total Session Number";
    }
    leaf mp-session-number {
      type uint32;
      description "MP Session Number";
    }
    leaf max-session-number {
      type uint32;
      description "Max Session Number";
    }
    leaf pps-all-percentage {
      type uint32;
      units "percentage";
      description "All PPS percentage";
    }
    leaf ppsmp-percentage {
      type uint32;
      units "percentage";
      description "MP PPS percentage";
    }
  }

  grouping BFD-MGMT-LSP-PING-INFO {
    description "BFD LSP Ping info";

    container lsp-ping-tx-last-time {
      description "LSP Ping last sent time";
      uses BFD-TIMESPEC;
    }

    container lsp-ping-tx-last-error-time {
      description "LSP Ping last error time";
      uses BFD-TIMESPEC;
    }

    container lsp-ping-rx-last-time {
      description "LSP Ping last received time";
      uses BFD-TIMESPEC;
    }
    leaf lsp-ping-tx-count {
      type uint32;
      description "LSP Ping Tx count";
    }
    leaf lsp-ping-tx-error-count {
      type uint32;
      description "LSP Ping Tx error count";
    }
    leaf lsp-ping-tx-last-rc {
      type string;
      description "LSP Ping Tx last result";
    }
    leaf lsp-ping-tx-last-error-rc {
      type string;
      description "LSP Ping Tx last error";
    }
    leaf lsp-ping-rx-last-discr {
      type Bfd-discr;
      description "LSP Ping Rx last received discriminator";
    }
    leaf lsp-ping-rx-count {
      type uint32;
      description "LSP Ping numer of times received";
    }
    leaf lsp-ping-rx-last-code {
      type uint8;
      description "LSP Ping Rx Last Code";
    }
    leaf lsp-ping-rx-last-subcode {
      type uint8;
      description "LSP Ping Rx Last Subcode";
    }
    leaf lsp-ping-rx-last-output {
      type string;
      description "LSP Ping Rx Last Output";
    }
  }

  grouping BFD-TIMESPEC {
    description "BFD TIMESPEC";
    leaf seconds {
      type uint64;
      units "second";
      description "seconds";
    }
    leaf nanoseconds {
      type uint32;
      units "nanosecond";
      description "nanoseconds";
    }
  }

  grouping BFD-MGMT-MP-DOWNLOAD-STATE-INFO {
    description "BFD Download State";

    container change-time {
      description "Change time";
      uses BFD-TIMESPEC;
    }
    leaf mp-download-state {
      type Bfd-mp-download-state;
      description "MP Download State";
    }
  }

  grouping BFD-MGMT-SESSION-ASSOCIATION-INFORMATION {
    description "BFD Session Association Information";

    container ip-destination-address {
      description "IPv4/v6 dest address";
      uses IP-ADDR-T-UNION;
    }
    leaf interface-name {
      type string {
        length "0..64";
      }
      description "Session Interface Name";
    }
    leaf sessiontype {
      type Bfd-session;
      description "Session type";
    }
    leaf local-discriminator {
      type Bfd-discr;
      description "Session's Local discriminator";
    }

    list owner-information {
      description "Client applications owning the session";
      uses BFD-MGMT-SESSION-OWNER-INFORMATION;
    }
  }

  grouping BFD-MGMT-SESSION-OWNER-INFORMATION {
    description "BFD Session Owner Information";
    leaf interval {
      type uint32;
      units "microsecond";
      description
        "Client specified minimum transmit interval in
        micro-seconds";
    }
    leaf detection-multiplier {
      type uint32;
      description
        "Client specified detection multiplier to compute
        detection time";
    }
    leaf adjusted-interval {
      type uint32;
      units "millisecond";
      description
        "Adjusted minimum transmit interval in
        milli-seconds";
    }
    leaf adjusted-detection-multiplier {
      type uint32;
      description
        "Adjusted detection multiplier to compute
        detection time";
    }
    leaf name {
      type string {
        length "0..257";
      }
      description "Client process name";
    }
  }

  grouping BFD-MGMT-INTERVAL-STATISTICS {
    description "BFD Agent Interval between packets Information";
    leaf number {
      type uint32;
      description
        "Number of Interval Samples between Packets
        sent/received";
    }
    leaf minimum {
      type uint32;
      units "millisecond";
      description
        "Minimum of Transmit/Receive Interval (in
        milli-seconds)";
    }
    leaf maximum {
      type uint32;
      units "millisecond";
      description
        "Maximum of Transmit/Receive Interval (in
        milli-seconds)";
    }
    leaf average {
      type uint32;
      units "millisecond";
      description
        "Average of Transmit/Receive Interval (in
        milli-seconds)";
    }
    leaf last {
      type uint32;
      units "millisecond";
      description
        "Time since last Transmit/Receive (in
        milli-seconds)";
    }
  }

  grouping BFD-MGMT-CONTROL-PACKET {
    description "BFD Control Packet";
    leaf version {
      type uint8;
      description "Version";
    }
    leaf diagnostic {
      type Bfd-mgmt-session-diag;
      description "Diagnostic";
    }
    leaf ihear-you {
      type int32;
      description "I Hear You (v0)";
    }
    leaf state {
      type Bfd-mgmt-session-state;
      description "State (v1)";
    }
    leaf demand {
      type int32;
      description "Demand mode";
    }
    leaf poll {
      type int32;
      description "Poll bit";
    }
    leaf final {
      type int32;
      description "Final bit";
    }
    leaf control-plane-independent {
      type int32;
      description
        "BFD implementation does not share fate with its
        control plane";
    }
    leaf authentication-present {
      type int32;
      description "Requesting authentication for the session";
    }
    leaf detection-multiplier {
      type uint32;
      description "Detection Multiplier";
    }
    leaf length {
      type uint32;
      description "Length";
    }
    leaf my-discriminator {
      type Bfd-discr;
      description "My Discriminator";
    }
    leaf your-discriminator {
      type Bfd-discr;
      description "Your Discriminator";
    }
    leaf desired-minimum-transmit-interval {
      type uint32;
      units "microsecond";
      description
        "Desired minimum transmit interval in
        micro-seconds";
    }
    leaf required-minimum-receive-interval {
      type uint32;
      units "microsecond";
      description "Required receive interval in micro-seconds";
    }
    leaf required-minimum-echo-receive-interval {
      type uint32;
      units "microsecond";
      description "Required echo receive interval in micro-seconds";
    }
  }

  grouping BFD-MGMT-SESSION-STATE-TIME {
    description "BFD Session State Transition Time Information";
    leaf days {
      type uint32;
      units "day";
      description
        "Number of days since last session state
        transition";
    }
    leaf hours {
      type uint8;
      units "hour";
      description
        "Number of hours since last session state
        transition";
    }
    leaf minutes {
      type uint8;
      units "minute";
      description
        "Number of mins since last session state
        transition";
    }
    leaf seconds {
      type uint8;
      units "second";
      description
        "Number of seconds since last session state
        transition";
    }
  }

  grouping IP-ADDR-T-UNION {
    description "IP ADDR T UNION";
    leaf afi {
      type Bfd-af-id;
      description "AFI";
    }
    leaf dummy {
      when "../afi = 'bfd-af-id-none'" {
        description "../AFI = 'BFD_AF_ID_NONE'";
      }
      type uint8;
      description "No Address";
    }
    leaf ipv4 {
      when "../afi = 'bfd-af-id-ipv4'" {
        description "../AFI = 'BFD_AF_ID_IPV4'";
      }
      type Bfd-in-addr;
      description "IPv4 address type";
    }
    leaf ipv6 {
      when "../afi = 'bfd-af-id-ipv6'" {
        description "../AFI = 'BFD_AF_ID_IPV6'";
      }
      type Bfd-in6-addr;
      description "IPv6 address type";
    }
  }

  grouping BFD-MGMT-SESSION-STATUS-INFORMATION {
    description "BFD Agent detailed Session Information";

    container source-address {
      description "Source address";
      uses IP-ADDR-T-UNION;
    }

    container last-state-change {
      description "Time since last state change";
      uses BFD-MGMT-SESSION-STATE-TIME;
    }

    container transmit-packet {
      description "Transmit Packet";
      uses BFD-MGMT-CONTROL-PACKET;
    }

    container receive-packet {
      description "Receive Packet";
      uses BFD-MGMT-CONTROL-PACKET;
    }

    container status-brief-information {
      description "Brief Status Information";
      uses BFD-MGMT-SESSION-STATUS-INFORMATION-BRIEF;
    }

    container async-transmit-statistics {
      description
        "Statistics of Interval between Async Packets
        Transmitted (in milli-seconds)";
      uses BFD-MGMT-INTERVAL-STATISTICS;
    }

    container async-receive-statistics {
      description
        "Statistics of Interval between Async Packets
        Received (in milli-seconds)";
      uses BFD-MGMT-INTERVAL-STATISTICS;
    }

    container echo-transmit-statistics {
      description
        "Statistics of Interval between Echo Packets
        Transmitted (in milli-seconds)";
      uses BFD-MGMT-INTERVAL-STATISTICS;
    }

    container echo-received-statistics {
      description
        "Statistics of Interval between Echo Packets
        Received (in milli-seconds)";
      uses BFD-MGMT-INTERVAL-STATISTICS;
    }
    leaf sessiontype {
      type Bfd-session;
      description "Session type";
    }
    leaf session-subtype {
      type string;
      description "Session subtype";
    }
    leaf state {
      type Bfd-mgmt-session-state;
      description "State";
    }
    leaf local-discriminator {
      type Bfd-discr;
      description "Session's Local discriminator";
    }
    leaf remote-discriminator {
      type Bfd-discr;
      description "Session's Remote discriminator";
    }
    leaf to-up-state-count {
      type uint32;
      description "Number of times session state went to UP";
    }
    leaf desired-minimum-echo-transmit-interval {
      type uint32;
      units "millisecond";
      description
        "Desired minimum echo transmit interval in
        milli-seconds";
    }
    leaf remote-negotiated-interval {
      type uint32;
      units "millisecond";
      description "Remote Negotiated Interval in milli-seconds";
    }
    leaf latency-number {
      type uint32;
      description
        "Number of Latency Samples. Time between Transmit
        and Receive";
    }
    leaf latency-minimum {
      type uint32;
      units "microsecond";
      description "Minimum value of Latency (in micro-seconds)";
    }
    leaf latency-maximum {
      type uint32;
      units "microsecond";
      description "Maximum value of Latency (in micro-seconds)";
    }
    leaf latency-average {
      type uint32;
      units "microsecond";
      description "Average value of Latency (in micro-seconds)";
    }
    leaf node-id {
      type xr:Node-id;
      description "Location where session is housed";
    }
    leaf internal-label {
      type uint32;
      description "Internal Label";
    }
  }

  grouping BFD-MGMT-SESSION-DETAIL {
    description "BFD Detailed Session Information";

    container status-information {
      description "Session status information";
      uses BFD-MGMT-SESSION-STATUS-INFORMATION;
    }

    container mp-download-state {
      description "MP Dowload State";
      uses BFD-MGMT-MP-DOWNLOAD-STATE-INFO;
    }

    container lsp-ping-info {
      description "LSP Ping Info";
      uses BFD-MGMT-LSP-PING-INFO;
    }

    list owner-information {
      description "Client applications owning the session";
      uses BFD-MGMT-SESSION-OWNER-INFORMATION;
    }

    list association-information {
      description "Association session information";
      uses BFD-MGMT-SESSION-ASSOCIATION-INFORMATION;
    }
  }

  grouping BFD-MGMT-MULTIPLE-PATHS {
    description "BFD Multiple paths Info";
    leaf session-subtype {
      type string;
      description "Session subtype";
    }
    leaf state {
      type Bfd-mgmt-session-state;
      description "State";
    }
    leaf local-discriminator {
      type Bfd-discr;
      description "Session's Local discriminator";
    }
    leaf node-id {
      type xr:Node-id;
      description "Location where session is housed";
    }
    leaf incoming-label-xr {
      type uint32;
      description "Incoming Label";
    }
    leaf session-interface-name {
      type xr:Interface-name;
      description "Interface name";
    }
  }

  grouping BFD-MGMT-CLIENT-FLAGS {
    description "BFD Client Flags";
    leaf is-zombie-state {
      type int32;
      description "Client is in Zombie State";
    }
    leaf is-recreate-state {
      type int32;
      description "Client is in Recreate State";
    }
  }

  grouping BFD-MGMT-CLIENT-BRIEF-INFORMATION {
    description "BFD Brief Client Information";
    leaf name-xr {
      type string {
        length "0..257";
      }
      description "Client process name";
    }
    leaf node-id {
      type xr:Node-id;
      description "Location where client resides";
    }
    leaf session-count {
      type uint32;
      description "Number of sessions created by this client";
    }
  }

  grouping BFD-MGMT-CLIENT-DETAIL-INFORMATION {
    description "BFD detailed Client Information";

    container brief {
      description "Brief client information";
      uses BFD-MGMT-CLIENT-BRIEF-INFORMATION;
    }

    container flags {
      description "The BFD Client Flags";
      uses BFD-MGMT-CLIENT-FLAGS;
    }
    leaf recreate-time {
      type uint32;
      units "second";
      description "Recreate Time in Seconds";
    }
  }

  grouping BFD-MGMT-PACKET-COUNT {
    description "BFD Agent Packet Count Info";
    leaf hello-transmit-count {
      type uint32;
      description "Number of Hellos transmitted";
    }
    leaf hello-receive-count {
      type uint32;
      description "Number of Hellos received";
    }
    leaf echo-transmit-count {
      type uint32;
      description "Number of echo packets transmitted";
    }
    leaf echo-receive-count {
      type uint32;
      description "Number of echo packets received";
    }
    leaf display-type {
      type Bfd-mgmt-pkt-display;
      description "Packet Display Type";
    }
  }

  grouping BFD-MGMT-SESSION-STATE-INFORMATION {
    description "BFD Session State Information";
    leaf total-count {
      type uint32;
      description "Number of sessions in database";
    }
    leaf down-count {
      type uint32;
      description "Number of sessions in down state";
    }
    leaf up-count {
      type uint32;
      description "Number of sessions in up state";
    }
    leaf unknown-count {
      type uint32;
      description "Number of sessions in unknown state";
    }
  }

  grouping BFD-MGMT-BFD-INFORMATION {
    description "BFD Summary Information";

    container session-state {
      description "Statistics of states for sessions";
      uses BFD-MGMT-SESSION-STATE-INFORMATION;
    }
  }

  grouping BFD-MGMT-ECHO-INTERVAL-MULTIPLIER-INFORMATION {
    description
      "BFD Agent Echo Interval and Detection Multiplier
      Information";
    leaf negotiated-transmit-interval {
      type uint32;
      units "microsecond";
      description "Negotiated transmit interval in micro-seconds";
    }
    leaf detection-time {
      type uint32;
      units "microsecond";
      description "Detection time in micro-seconds";
    }
    leaf detection-multiplier {
      type uint32;
      description "Detection Multiplier";
    }
  }

  grouping BFD-MGMT-ASYNC-INTERVAL-MULTIPLIER-INFORMATION {
    description
      "BFD Agent Async Interval and Detection Multiplier
      Information";
    leaf negotiated-remote-transmit-interval {
      type uint32;
      units "microsecond";
      description
        "Negotiated remote transmit interval in
        micro-seconds";
    }
    leaf negotiated-local-transmit-interval {
      type uint32;
      units "microsecond";
      description
        "Negotiated local transmit interval in
        micro-seconds";
    }
    leaf detection-time {
      type uint32;
      units "microsecond";
      description "Detection time in micro-seconds";
    }
    leaf detection-multiplier {
      type uint32;
      description "Detection Multiplier";
    }
  }

  grouping BFD-MGMT-SESSION-STATUS-INFORMATION-BRIEF {
    description "BFD Session Status Brief Information ";

    container async-interval-multiplier {
      description
        "Async Interval and Detect Multiplier Information";
      uses BFD-MGMT-ASYNC-INTERVAL-MULTIPLIER-INFORMATION;
    }

    container echo-interval-multiplier {
      description "Echo Interval and Detect Multiplier Information";
      uses BFD-MGMT-ECHO-INTERVAL-MULTIPLIER-INFORMATION;
    }
  }

  grouping BFD-MGMT-SESSION-BRIEF {
    description "BFD Brief Session Information";

    container status-brief-information {
      description "Brief Status Information";
      uses BFD-MGMT-SESSION-STATUS-INFORMATION-BRIEF;
    }
    leaf node-id {
      type xr:Node-id;
      description "Location where session is housed";
    }
    leaf state {
      type Bfd-mgmt-session-state;
      description "State";
    }
    leaf session-type {
      type Bfd-session;
      description "Session type";
    }
    leaf session-subtype {
      type string;
      description "Session subtype";
    }
    leaf session-flags {
      type uint32;
      description "Session Flags";
    }
  }
}
