module Cisco-IOS-XR-infra-tc-cfg {

  /*** NAMESPACE / PREFIX DEFINITION ***/

  namespace "http://cisco.com/ns/yang/Cisco-IOS-XR-infra-tc-cfg";


  prefix "infra-tc-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-tc package configuration.

     This module contains definitions
     for the following management objects:
       traffic-collector: Global Traffic Collector configuration
         commands

     Copyright (c) 2013-2018 by Cisco Systems, Inc.
     All rights reserved.";

  revision "2015-11-09" {
    description
      "IOS XR 6.0 revision.";
  }

  typedef History-size {
    type union {
      type enumeration {
        enum max {
          value 10;
          description "Max history";
        }
      }
      type uint32 {
        range "1..10";
      }
    }
    description "History size";
  }
  typedef Collect-ion-interval {
    type enumeration {
      enum 1-minute {
        value 1;
        description "Interval1minute";
      }
      enum 2-minutes {
        value 2;
        description "Interval2minutes";
      }
      enum 3-minutes {
        value 3;
        description "Interval3minutes";
      }
      enum 4-minutes {
        value 4;
        description "Interval4minutes";
      }
      enum 5-minutes {
        value 5;
        description "Interval5minutes";
      }
      enum 6-minutes {
        value 6;
        description "Interval6minutes";
      }
      enum 10-minutes {
        value 10;
        description "Interval10minutes";
      }
      enum 12-minutes {
        value 12;
        description "Interval12minutes";
      }
      enum 15-minutes {
        value 15;
        description "Interval15inutes";
      }
      enum 20-minutes {
        value 20;
        description "Interval20minutes";
      }
      enum 30-minutes {
        value 30;
        description "Interval30minutes";
      }
      enum 60-minutes {
        value 60;
        description "Interval60minutes";
      }
    }
    description "Collect ion interval";
  }
  typedef History-timeout {
    type union {
      type enumeration {
        enum max {
          value 720;
          description "Max timeout";
        }
      }
      type uint32 {
        range "0..720";
      }
    }
    description "History timeout";
  }

  container traffic-collector {
    description "Global Traffic Collector configuration commands";

    container external-interfaces {
      description "Configure external interfaces";

      list external-interface {
        key "interface-name";
        description "Configure an external internface";
        leaf enable {
          type empty;
          description "Enable traffic collector on this interface";
        }
        leaf interface-name {
          type xr:Interface-name;
          description "Name of interface";
        }
      }
    }

    container statistics {
      description "Configure statistics related parameters";
      leaf history-size {
        type History-size;
        description "Configure statistics history size";
      }
      leaf collection-interval {
        type Collect-ion-interval;
        description "Configure statistics collection interval";
      }
      leaf enable-traffic-collector-statistics {
        type empty;
        description "Enable traffic collector statistics";
      }
      leaf history-timeout {
        type History-timeout;
        description "Configure statistics history timeout interval";
      }
    }
    leaf enable-traffic-collector {
      type empty;
      description "Enable traffic collector";
    }
  }
}
