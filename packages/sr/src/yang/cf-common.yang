module cf-common {
  namespace "http://cisco.com/nso/cf-common";
  prefix cfcommon;

  import tailf-common {
    prefix tailf;
  }

  import resource-allocator {
    prefix ralloc;
  }
  import ipaddress-allocator {
    prefix ipalloc;
  }
  import id-allocator {
    prefix idalloc;
  }

  organization "Cisco Network Services orchestrator";
  description
    "This yang has reusable segment-routing groupings , typedefs etc";


  revision 2018-07-23 {
    description
      "This yang has resuable segment-routing groupings , typedefs etc";
  }

  grouping pools-grouping {
    description
      "All id-pools and ip-address pools required for the campus-fabric.";

   list sr-global-block-pools {
      description
        "Pools which generates prefix-sid for P Routers";
      tailf:info "SR Global Block Range";
      key "name";
      leaf name {
        type leafref {
          path "/ralloc:resource-pools/idalloc:id-pool/idalloc:name";
        }
      }
    }
  }

  grouping sr-mpls-choice {
    description
      "Allows to set segment routing mpls prefer vs segment routing mpls on the segment routing.";
    container sr-mpls-preference {
      tailf:info "Specify segment-routing mpls sr-prefer or segment-routing mpls";
      choice sr-mpls-prefer-choice {
        default sr-mpls;
        leaf sr-prefer {
          tailf:info "This will enable segment-routing mpls sr-prefer";
            type empty;
        }
        leaf sr-mpls {
          tailf:info "This will enable segment-routing mpls";
	  type empty;
       }
     }
   }
 }

  grouping pickinterfaces {
  description
      "Grouping that defines ability to provide user a choice to pick up all interfaces on a device or let user specify list of interfaces that needs to be configured with TI-LFA(Toplogy Independent Loop Free Alternative)";
   container interface-preference {
   tailf:info "Allows user to pick all interfaces or specify few interfaces on a P Router that needs to be configured with ti-lfa";
    choice interfaces {
      leaf all-interfaces {
      tailf:info "All interfaces will be applied ti-fla configuration excluding Loopback under the instance name";
        type empty;
      }
      list select-interface {
        tailf:info "Name the interfaces to apply ti-fla configuration";
        key "interface-type interface-id";

        leaf interface-type {
          tailf:info "Interface Type";
          type int-type;
        }
        leaf interface-id {
         when "../interface-type!=''";
         tailf:info " Interface ID";
         mandatory true;
         type int-id;
       }
      }
     }
    }
  }

  grouping instance-name-choice-grouping {
  description "Grouping that defines ability to provide user a choice between a custom instance name or use a common instance name from a global sr-infrastructure model. It may be possible that many devices has same instance name while some have different. Used in TI-LFA.";
    container instance-name-preference {
      tailf:info "Allows a user to pick a already defined ISIS instance name  or choose a new custom specific to the device";
      choice instance-name-choice {
        leaf use-sr-infrastructure {
          tailf:info "A user defined instance name that is common across most of devices will be read from sr-infrastructure and configured on the device.";
          type empty;
        }
        container custom-instance {
         leaf instance-name {
           tailf:info "Custom ISIS instance name for this device";
           type string;
           default "";
         }
        }
       }
     }
   }

   typedef int-type {
      type enumeration {
          enum GigabitEthernet;
          enum TenGigabitEthernet;
          enum FortyGigabitEthernet;
          enum HundredGigabitEthernet;
          enum Bundle-Ether ;
      }
   }

   typedef member-int-type {
      type enumeration {
          enum GigabitEthernet;
          enum TenGigabitEthernet;
          enum FortyGigabitEthernet;
          enum HundredGigabitEthernet;
      }
   }

   typedef int-id {
      type string {
          pattern "[0-9]+.*";
      }
   }

  grouping instance-loopback-grouping{
   description " Grouping that encapsulates instance-name and loopback that is basis of the Segment Routing Configuration";
   leaf instance-name {
      tailf:info "ISIS instance name";
      type string;
      default "";
    }

   leaf loopback {
      tailf:info "IS-IS loopback for prefix-sid";
        type uint32 {
           range "0..2147483647";
        }
        default 0;
     }
  }

  grouping prefix-choice-grouping {
   description "Grouping that allows user to pick a choice to let NSO assign a prefix sid id from a pool or let user define it.It is to the admin to ensure that he does not pick up a id that is already allocated by NSO.";
    container prefix-preference {
      tailf:info " Allows user to pick a prefix-sid or let Orchestartion assign one that will be configured on the P Router device";
      choice prefix-choice {
        leaf auto-assign-prefix-sid {
          tailf:info "NSO auto assigns a prefix sid for a device from a id pool defined in the sr-infrastructure";
          type empty;
        }
	leaf assign-prefix-sid {
          tailf:info "Assign a non used prefix-sid between the allowed range 16000 to 23999 to a device";
          type uint16 {
            tailf:info "Pick a non used prefix-sid between the allowed range 16000 to 23999";
            range "16000..23999";
          }
         }
	}
      }
   }

  grouping instance-choice-grouping {
 description "Grouping that defines ability to provide user a choice between a custom instance name and its loopback or use a common instance name from a global sr-infrastructure model. It may be possible that many devices has same instance name and loopback while some have different.";
    container instance-preference {
      tailf:info "Allows a user to pick a already defined ISIS instance name and loopback or choose a new custom specific to the device";
      choice instance-choice {
        leaf use-sr-infrastructure {
          tailf:info "A user defined instance name and loopback that is common across most of devices will be read from sr-infrastructure and configured on the device.";
          type empty;
        }
        container custom-instance {
          uses instance-loopback-grouping;
        }
       }
     }
   }
}
